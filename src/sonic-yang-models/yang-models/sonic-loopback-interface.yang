module sonic-loopback-interface {

    yang-version 1.1;

    namespace "http://github.com/sonic-net/sonic-loopback-interface";
    prefix lointf;

    import sonic-types {
        prefix stypes;
    }

    import sonic-vrf {
        prefix vrf;
    }

    import sonic-vnet {
        prefix svnet;
    }

    description
        "Loopback interface configuration for virtual interfaces used as router IDs and service IPs";

    revision 2026-09-12 {
        description "Add leaf description and leaf vnet_name";
    }

    revision 2021-04-05 {
        description "Modify the type of vrf name";
    }

    revision 2020-02-05 {
        description "First Revision";
    }

    container sonic-loopback-interface {

        container LOOPBACK_INTERFACE {

            description "Loopback interface configuration table";

            list LOOPBACK_INTERFACE_LIST {
                description "Configuration entry for a loopback interface including VRF binding and properties";

                key "name";

                leaf name{
                    description "Loopback interface name (e.g. Loopback0)";
                    type stypes:interface_name;
                }

                leaf vrf_name {
                    description "VRF instance to which this loopback interface is bound";
                    type leafref {
                        path "/vrf:sonic-vrf/vrf:VRF/vrf:VRF_LIST/vrf:name";
                    }
                }

                leaf vnet_name {
                    description "Reference to the name of a VNET in sonic-vnet model";
                    type leafref {
                        path "/svnet:sonic-vnet/svnet:VNET/svnet:VNET_LIST/svnet:name";
                    }
                }

                leaf description {
                    description "User-defined description for the loopback interface";
                    type string {
                        length 0..255 {
                            error-message "Invalid description length, it must not exceed 255 characters.";
                        }
                    }
                }

                leaf nat_zone {
                    description "NAT Zone for the loopback interface";
                    type uint8 {
                        range "0..3" {
                            error-message "Invalid nat zone for the loopback interface.";
                            error-app-tag nat-zone-invalid;
                        }
                    }
                    default "0";
                }

                leaf admin_status {
                    description "Administrative state of the loopback interface";
                    type stypes:admin_status;
                    default up;
                }
            }
            /* end of LOOPBACK_INTERFACE_LIST */

            list LOOPBACK_INTERFACE_IPPREFIX_LIST {

                description "IP address prefix assignment for a loopback interface";

                key "name ip-prefix";

                leaf name{
                    description "Loopback interface name";

                    type leafref {
                        path "../../LOOPBACK_INTERFACE_LIST/name";
                    }
                }

                leaf ip-prefix {
                    description "IPv4 or IPv6 address with prefix length assigned to the loopback interface";
                    type union {
                        type stypes:sonic-ip4-prefix;
                        type stypes:sonic-ip6-prefix;
                    }
                }

                leaf scope {
                    description "Address scope indicating global or link-local reachability";
                    type enumeration {
                        enum global;
                        enum local;
                    }
                }

                leaf family {
                    description "IP address family, must match the format of ip-prefix";

                    /* family leaf needed for backward compatibility
                       Both ip4 and ip6 address are string in IETF RFC 6021,
                       so must statement can check based on : or ., family
                       should be IPv4 or IPv6 according.
                     */

                    must "(contains(../ip-prefix, ':') and current()='IPv6') or
                        (contains(../ip-prefix, '.') and current()='IPv4')";
                    type stypes:ip-family;
                }
            }
        }
        /* end of LOOPBACK_INTERFACE_IPPREFIX_LIST */
    }
}
