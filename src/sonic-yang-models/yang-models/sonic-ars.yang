module sonic-ars {
    namespace "http://github.com/sonic-net/sonic-ars";
    prefix sars;
    yang-version 1.1;

    import ietf-yang-types {
        prefix yang;
    }

    import ietf-inet-types {
        prefix inet;
    }

    import sonic-types {
        prefix stypes;
    }

	import sonic-vrf {
		prefix vrf;
	}

    import sonic-port {
        prefix port;
    }

    organization
        "SONiC";

    contact
        "SONiC";

    description
        "SONIC Adaptive Routing and Switching";

    revision 2025-10-30 {
        description "Initial revision of ARS YANG model.";
    }

    container sonic-ars {
    container ARS_PROFILE {
        list ARS_PROFILE_LIST {
            key "profile_name";
            max-elements 1;
            leaf profile_name {
                description "ARS Profile Name";
                type string;
            }
            leaf algorithm {
                description "ARS quality algorithm";
                type enumeration {
                    enum ewma {
                    description "Exponentially Weighted Moving Average algorithm";
                    }
                }
            }
            leaf ars_nhg_path_selector_mode {
                description "ARS selection mode for nexthop (global/interface/nexthop)";
                type enumeration {
                    enum global {
                        description "ARS object selection is global.";
                    }
                    enum interface {
                        description "Uses list of configured interfaces for ARS object selection.";
                    }
                    enum nexthop {
                        description "Uses list of configured nexthops for ARS object selection.";
                    }
                }
                default "interface";
            }

            leaf ars_lag_path_selector_mode {
                description "ARS selection mode for LAG (global/interface)";
                type enumeration {
                    enum global {
                        description "ARS LAG selection is global.";
                    }
                    enum interface {
                        description "Uses list of configured interfaces for ARS LAG selection.";
                    }
                }
                default "interface";
            }

            leaf default_ars_object {
                description "Default ARS object name for both nexthop group and LAG.";
                type leafref {
                    path "/sars:sonic-ars/sars:ARS_OBJECT/sars:ARS_OBJECT_LIST/sars:ars_obj_name";
                }
              }

            leaf max_flows {
                type uint32;
                description  "Maximum number of flows that can be maintained per ARS profile.";
            }

            leaf sampling_interval {
                type uint32;
                description  "Sampling interval in microseconds for quality measure computation.";
            }

            leaf past_load_min_value {
                type uint16;
                description "Past load min value.";
            }

            leaf past_load_max_value {
                type uint16;
                description "Past load max value.";
            }

            leaf past_load_weight {
                type uint16;
                description "Past load weight.";
            }

            leaf future_load_min_value {
                type uint16;
                description "Future load min value.";
            }

            leaf future_load_max_value {
                type uint16;
                description "Future load max value.";
            }

            leaf future_load_weight {
                type uint16;
                description "Future load weight.";
            }

            leaf current_load_min_value {
                type uint16;
                description "Current load min value.";
            }

            leaf current_load_max_value {
                type uint16;
                description "Current load max value.";
            }

            leaf ipv4_enable {
                type boolean;
                description "Whether ARS is enabled over IPv4 packets";
            }

            leaf ipv6_enable {
                type boolean;
                description "Whether ARS is enabled over IPv6 packets";
            }
        }
        /* end of list ARS_PROFILE_LIST */
    }
    /* end of container ARS_PROFILE */
    container ARS_INTERFACE {
            list ARS_INTERFACE_LIST {
                description  "List of interfaces participating in ARS";
                    key "if_name";
                    leaf if_name {
                type union {
                type leafref {
                    path "/port:sonic-port/port:PORT/port:PORT_LIST/port:name";
                }
                    }
                description "ARS-enabled interface name";
            }

            leaf scaling_factor {
                type uint32;
                default "1";
                description "This factor used to normalize load measurements across ports with different speeds.";
            }
                        leaf ars_obj_name {
                            description "ARS object name, inherited from 'default_ars_object' unless explicitly configured.";
                            type leafref {
                                path "/sars:sonic-ars/sars:ARS_OBJECT/sars:ARS_OBJECT_LIST/sars:ars_obj_name";
                            }
                        }
        }
        /* end of list ARS_INTERFACE_LIST */
    }
    /* end of container ARS_INTERFACE */

    container ARS_NEXTHOP {
        description "ARS-enabled Nexthop Groups";
        list ARS_NEXTHOP_LIST {
            key "vrf_name nexthop_ip";
            leaf vrf_name {
                type union {
                    type string {
                        pattern "default";
                    }
                    type leafref {
                        path "/vrf:sonic-vrf/vrf:VRF/vrf:VRF_LIST/vrf:name";
                    }
                }
                description "VRF name";
            } 
            leaf nexthop_ip{
                type inet:ip-address;
                description "Nexthop IP which is a member of a nexthop group for which ARS behavior is desired.";
            }
                        leaf ars_obj_name {
                            description "ARS object name, inherited from 'default_ars_object' unless explicitly configured.";
                            type leafref {
                                path "/sars:sonic-ars/sars:ARS_OBJECT/sars:ARS_OBJECT_LIST/sars:ars_obj_name";
                            }
                        }

                        leaf role {
                            type enumeration {
                                enum primary_path {
                                    description "Member is participating in primary path.";
                                }
                                enum alternative_path {
                                    description "Member is participating in alternative path.";
                                }
                            }
                            default primary_path;
                            description "NHG member's role.";
                        }
        }
        /* end of list ARS_NEXTHOP_LIST */
    }
    /* end of container ARS_NEXTHOP */
    container ARS_OBJECT {
        description "ARS-enabled Object Groups";
        list ARS_OBJECT_LIST {
            key "ars_obj_name";
            leaf ars_obj_name {
                description "ARS Object Name";
                type string;
            }
            leaf assign_mode {
                type enumeration {
                    enum per_flowlet_quality{
                        description "Per flow-let assignment based on flow quality";
                    }
                    enum per_packet_quality {
                        description "Per packet flow assignment based on port load";
                    }
                }
            }
            leaf flowlet_idle_time {
                type uint16 {
                    range 2..2047;
                }
                description  "Idle duration in microseconds. This duration is to classifying a flow-let in a macro flow.";
            }
            leaf max_flows {
                type uint32;
                description  "Maximum number of flow states that can be maintained per ARS object.";
            }
            leaf primary_path_threshold {
                type uint32;
                default "16";
                description  "Primary path metric threshold.";
            }
            leaf alternative_path_cost {
                type uint32;
                default "0";
                description  "Alternative path cost.";
            }
        }
        /* end of list ARS_OBJECT_LIST */
        }
    /* end of container ARS_OBJECT */
    }
}
