module sonic-mux-cable {
    namespace "http://github.com/sonic-net/sonic-mux-cable";
    prefix mux_cable;
    yang-version 1.1;

    import ietf-inet-types {
        prefix inet;
    }

    import sonic-port {
        prefix prt;
    }

    organization
        "SONiC";

    contact
        "SONiC";

    description
        "Dual-ToR mux cable state and configuration per port";

    revision 2026-06-01 {
        description
            "Add server_ipv6_subnet leaf for mux subnet slicing.";
    }

    revision 2022-08-19 {
        description
            "Initial revision";
    }

    container sonic-mux-cable {

        container MUX_CABLE {

            list MUX_CABLE_LIST {

                key "ifname";

                leaf ifname {
                    type leafref {
                        path "/prt:sonic-port/prt:PORT/prt:PORT_LIST/prt:name";
                    }
                    description
                        "Reference of port on which MUX cable to be configured.";
                }

                leaf cable_type {
                    type enumeration {
                        enum active-active;
                        enum active-standby;
                    }
                    default active-standby;
                    description "SONiC DualToR interface cable type.";
                }

                leaf prober_type {
                    type enumeration {
                        enum hardware;
                        enum software;
                    }
                    default software;
                    description "DualToR LinkMrgrd Icmp Prober mode.";
                }

                leaf neighbor_mode {
                    type enumeration {
                        enum prefix-route;
                        enum host-route;
                    }
                    default host-route;
                    description "DualToR MUX neighbor mode.";
                }

                leaf server_ipv4 {
                    type inet:ipv4-prefix;

                    description "Server IPv4 Address.";
                }

                leaf server_ipv6 {
                    type inet:ipv6-prefix;

                    description "Server IPv6 Address.";
                }

                leaf soc_ipv4 {
                    type inet:ipv4-prefix;

                    description "SoC IPv4 address. Optional and for active-active ports only. ";
                }

                leaf soc_ipv6 {
                    type inet:ipv6-prefix;

                    description "SoC IPv6 address. Optional and for active-active ports only. ";
                }

                leaf server_ipv6_subnet {
                    type inet:ipv6-prefix;
                    description
                        "Optional IPv6 subnet of server-facing neighbors that participate in mux subnet slicing. When set, neighbors whose IPv6 address falls within this prefix are eligible for slice-based suppression by orchagent. Immutable once set (enforced at runtime).";
                }

                leaf state {
                    type enumeration {
                        enum auto;
                        enum manual;
                        enum detach;
                        enum active;
                        enum standby;
                    }

                    default auto;
                    description "MUX mode determining if auto failover is enabled. ";
                }
            }
        }
    }
}
