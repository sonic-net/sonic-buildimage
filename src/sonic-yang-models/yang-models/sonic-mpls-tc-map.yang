module sonic-mpls-tc-map {

    yang-version 1.1;

    namespace "http://github.com/sonic-net/sonic-mpls-tc-map";

    prefix mpls_tc_map;

    import sonic-types {
        prefix stypes;
    }

    organization
        "SONiC";

    contact
        "SONiC";

    description
        "MPLS_TC_TO_TC_MAP configuration";

    revision 2021-04-15 {
        description
            "Initial revision.";
    }

    container sonic-mpls-tc-map {

        container MPLS_TC_TO_TC_MAP {

            description "Maps MPLS TC bits to traffic class for QoS classification of MPLS traffic.";

            list MPLS_TC_TO_TC_MAP_LIST {

                key "name";

                description "A named MPLS TC to traffic class map.";

                leaf name {
                    description "Name of the MPLS TC to TC map.";
                    type string {
                        pattern '[a-zA-Z0-9]{1}([-a-zA-Z0-9_]{0,31})';
                        length 1..32 {
                            error-message "Invalid length for map name.";
                            error-app-tag map-name-invalid-length;
                        }
                    }
                }

                list MPLS_TC_TO_TC_MAP {

                    key "mpls";

                    description "Single mapping entry from an MPLS TC value to a traffic class.";

                    leaf mpls {
                        description "MPLS TC Value";
                        type string {
                            pattern "[0-7]?" {
                                error-message "Invalid MPLS";
                                error-app-tag mpls-invalid;
                            }
                        }
                    }

                    leaf tc {
                        description "Matching TC Value";
                        type stypes:tc_type;
                    }
                }
            }
        }
    }
}
