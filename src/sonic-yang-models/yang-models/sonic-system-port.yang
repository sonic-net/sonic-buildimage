module sonic-system-port {

    yang-version 1.1;

    namespace "http://github.com/sonic-net/sonic-system-port";
    prefix system-port;

    import sonic-types {
        prefix stypes;
    }

    description "VoQ system port configuration YANG module for SONiC OS.";

    revision 2022-11-10 {
        description "First Revision";
    }

    container sonic-system-port {

        container SYSTEM_PORT {

            description "System port definitions for VoQ-based distributed switch architectures.";

            list SYSTEM_PORT_LIST {

                key "hostname asic_name ifname";
                description "A system port entry uniquely identified by host, ASIC, and interface name.";

                leaf hostname {
                    type stypes:hostname;
                    description "Hostname of the switch owning this port.";
                }

                leaf asic_name {
                    type stypes:asic_name;
                    description "ASIC namespace name within the switch.";
                }

                leaf ifname {
                    type string {
                        length 1..128;
                    }
                    description "Interface name of the port on the specified ASIC.";
                }

                leaf core_index {
                    type uint8 {
                        range 0..7;
                    }
                    description "Hardware core index a port is affiliated with.";
                }

                leaf core_port_index {
                    type uint16;
                    description "Local port index index to an ASIC core.";
                }

                leaf num_voq {
                    type uint8 {
                        range 1..8;
                    }
                    description "Number of VoQs associated with a port.";
                }

                leaf speed {
                    type uint32 {
                        range 1..800000;
                    }
                    description "Port speed in Mbps.";
                }

                leaf switch_id {
                    type uint16;
                    description "On a VoQ switch, the global ASIC identifier.";
                }

                leaf system_port_id {
                    type uint32;
                    description "On a VoQ switch, the global port identifier.";
                }
            }
            /* end of list SYSTEM_PORT_LIST */
        }
        /* end of container SYSTEM_PORT */
    }
    /* end of container sonic-system-port */
}
/* end of module sonic-system-port */
