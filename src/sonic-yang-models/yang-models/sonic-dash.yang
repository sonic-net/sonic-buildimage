module sonic-dash {

    yang-version 1.1;

    namespace "http://github.com/Azure/sonic-dash";
    prefix dash;

    import ietf-yang-types {
        prefix yang;
    }

    import ietf-inet-types {
        prefix inet;
    }

    import sonic-types {
        prefix stypes;
    }

    organization
        "SONiC";

    contact
        "SONiC";

    description
        "Disaggregated API for Hosts (DASH) SmartNIC/DPU overlay configuration.";

    revision 2022-12-07 {
        description
            "Initial revision.";
    }

    container sonic-dash {

        container DASH_VNET {

            description "DASH virtual network definitions with VNI and address space.";

            list DASH_VNET_LIST {
                key "name";

                leaf name {
                    description "Virtual network name.";
                    type string {
                        pattern "Vnet[a-zA-Z0-9_-]+" {
                            error-message "Invalid Vnet name";
                            error-app-tag vnet-name-invalid;
                        }
                    }
                }

                leaf vni {
                    description "VXLAN Network Identifier for the virtual network.";
                    type  uint32 {
                        range 1..16777215;
                    }
                }

                leaf guid {
                    description "Guid used for Vnet identification";
                    type string {
                        length 1..255;
                    }
                }

                leaf-list address_spaces {
                     description "IP prefixes belonging to this virtual network.";
                     type stypes:sonic-ip-prefix;
                     ordered-by user;
                }

            } /* end of list DASH_VNET_LIST */
        } /* end of container DASH_VNET */

        container DASH_QOS {
            description "DASH QoS profiles specifying bandwidth, connection, and flow limits.";

            list DASH_QOS_LIST {
                key "name";

                leaf name{
                    description "QoS profile name.";
                    type string {
                        length 1..255;
                    }
                }

                leaf bw {
                    description "Bandwidth in kbps";
                    type uint64 {
                        range "0..100000000" {
                            error-message "kbps value out of range";
                        }
                    }
                }

                leaf cps {
                    description "Max number of connections per second";
                    type uint64 {
                        range "0..100000000" {
                            error-message "cps value out of range";
                        }
                    }
                }

                leaf flows {
                    description "Number of flows";
                    type uint64 {
                        range "0..100000000" {
                            error-message "flows value out of range";
                        }
                    }
                }

            } /* end of list DASH_QOS_LIST */
        } /* end of container DASH_QOS */

        container DASH_ENI {
            description "DASH Elastic Network Interface (ENI) configuration.";

            list DASH_ENI_LIST {
                key "name";

                leaf name{
                    description "ENI name.";
                    type string {
                        length 1..255;
                    }
                }

                leaf eni_id{
                    description "ENI guid for cross reference and identification";
                    type string {
                        length 1..255;
                    }
                }

                leaf mac_address {
                    description "MAC address of the ENI.";
                    type yang:mac-address;
                }

                leaf qos {
                    description "Reference to the QoS profile applied to this ENI.";
                    type leafref {
                        path /dash:sonic-dash/dash:DASH_QOS/dash:DASH_QOS_LIST/dash:name;
                    }
                }

                leaf vnet {
                    description "Reference to the virtual network this ENI belongs to.";
                    type leafref {
                        path /dash:sonic-dash/dash:DASH_VNET/dash:DASH_VNET_LIST/dash:name;
                    }
                }

            } /* end of list DASH_ENI_LIST */
        } /* end of container DASH_ENI */

        container DASH_ACL_IN {
            description "DASH ingress ACL bindings associating an ENI stage with an ACL group.";

            list DASH_ACL_IN_LIST {
                key "eni stage";

                leaf eni {
                    description "Reference to the ENI this ingress ACL applies to.";
                    type leafref {
                        path /dash:sonic-dash/dash:DASH_ENI/dash:DASH_ENI_LIST/dash:name;
                    }
                }

                leaf stage {
                    description "ACL pipeline stage number.";
                    type  uint8 {
                        range 1..5;
                    }
                }

                leaf acl_group_id {
                    description "Reference to the ACL group applied at this stage.";
                    type leafref {
                        path /dash:sonic-dash/dash:DASH_ACL_GROUP/dash:DASH_ACL_GROUP_LIST/dash:name;
                    }
                }

            } /* end of list DASH_ACL_IN_LIST */
        } /* end of container DASH_ACL_IN */

        container DASH_ACL_OUT {
            description "DASH egress ACL bindings associating an ENI stage with an ACL group.";

            list DASH_ACL_OUT_LIST {
                key "eni stage";

                leaf eni {
                    description "Reference to the ENI this egress ACL applies to.";
                    type leafref {
                        path /dash:sonic-dash/dash:DASH_ENI/dash:DASH_ENI_LIST/dash:name;
                    }
                }

                leaf stage {
                    description "ACL pipeline stage number.";
                    type  uint8 {
                        range 1..5;
                    }
                }

                leaf acl_group_id {
                    description "Reference to the ACL group applied at this stage.";
                    type leafref {
                        path /dash:sonic-dash/dash:DASH_ACL_GROUP/dash:DASH_ACL_GROUP_LIST/dash:name;
                    }
                }

            } /* end of list DASH_ACL_OUT_LIST */
        } /* end of container DASH_ACL_OUT */

        container DASH_ACL_GROUP {
            description "DASH ACL group defining the IP version for a set of ACL rules.";

            list DASH_ACL_GROUP_LIST {
                key "name";

                leaf name {
                    description "ACL group name.";
                    type string {
                        length 1..255;
                    }
                }

                leaf ip_version {
                    description "IP version (ipv4 or ipv6) for rules in this group.";
                    type string {
                        pattern "ipv4|ipv6";
                    }
                }

                leaf guid {
                    description "Globally unique identifier for this ACL group.";
                    type string {
                        length 1..255;
                    }
                }

            } /* end of list DASH_ACL_GROUP_LIST */
        } /* end of container DASH_ACL_GROUP */

        container DASH_ACL_RULE {
            description "DASH ACL rules with match criteria and allow/deny actions.";

            list DASH_ACL_RULE_LIST {
                key "acl_group_id name";

                leaf acl_group_id {
                    description "Reference to the ACL group this rule belongs to.";
                    type leafref {
                        path /dash:sonic-dash/dash:DASH_ACL_GROUP/dash:DASH_ACL_GROUP_LIST/dash:name;
                    }
                }

                leaf name {
                    description "ACL rule name.";
                    type string {
                        length 1..255;
                    }
                }

                leaf priority {
                    description "Rule evaluation priority, lower values are evaluated first.";
                    type  uint32 {
                        range 0..16777215;
                    }
                }

                leaf action {
                    description "Allow or deny matching traffic.";
                    type string {
                        pattern "allow|deny";
                    }
                }

                leaf terminating {
                    type boolean;
                    default false;
                    description "If set to true, stop processing further rules";
                }

                leaf-list ip_protocol {
                    description "IP Protocol (tcp or udp or icmp etc)";
                    type stypes:ip-protocol-type;
                    ordered-by user;
                }

                leaf-list src_addr {
                    description "Source IP prefixes to match.";
                    type stypes:sonic-ip-prefix;
                    ordered-by user;
                }

                leaf-list dst_addr {
                    description "Destination IP prefixes to match.";
                    type stypes:sonic-ip-prefix;
                    ordered-by user;
                }

                leaf-list src_port {
                     description "List of L4 source port range as pattern '0-65365'";
                     type string {
                         pattern '([0-9]{1,4}|[0-5][0-9]{4}|[6][0-4][0-9]{3}|[6][5][0-2][0-9]{2}|[6][5][3][0-5]{2}|[6][5][3][6][0-5])-([0-9]{1,4}|[0-5][0-9]{4}|[6][0-4][0-9]{3}|[6][5][0-2][0-9]{2}|[6][5][3][0-5]{2}|[6][5][3][6][0-5])';
                     }
                     ordered-by user;
                }

                leaf-list dst_port {
                     description "List of L4 dst port range as pattern '0-65365'";
                     type string {
                         pattern '([0-9]{1,4}|[0-5][0-9]{4}|[6][0-4][0-9]{3}|[6][5][0-2][0-9]{2}|[6][5][3][0-5]{2}|[6][5][3][6][0-5])-([0-9]{1,4}|[0-5][0-9]{4}|[6][0-4][0-9]{3}|[6][5][0-2][0-9]{2}|[6][5][3][0-5]{2}|[6][5][3][6][0-5])';
                     }
                     ordered-by user;
                }

            } /* end of list DASH_ACL_RULE_LIST */
        } /* end of container DASH_ACL_RULE */

        container DASH_APPLIANCE {
            description "DASH appliance-level configuration for SmartNIC/DPU devices.";

            list DASH_APPLIANCE_LIST {
                key "name";

                leaf name {
                    description "Appliance name.";
                    type string {
                        length 1..255;
                    }
                }

                leaf sip {
                     description "Source IP address of the appliance.";
                     type inet:ip-address;
                }

                leaf vni {
                    description "VM VNI used for determining packet direction.";
                    type  uint32 {
                        range 1..16777215;
                    }
                }

            } /* end of list DASH_APPLIANCE_LIST */
        } /* end of container DASH_APPLIANCE */

        container DASH_ROUTING_TYPE {
            description "DASH routing type definitions mapping names to forwarding actions and encapsulation.";

            list DASH_ROUTING_TYPE_LIST {
                key "name";

                leaf name {
                    description "Routing type identifier.";
                    type string {
                        pattern "direct|vnet|vnet_direct|vnet_encap|drop|appliance|privatelink|privatelinknsg|servicetunnel";
                    }
                }

                leaf action_name {
                    description "Name of the forwarding action.";
                    type string {
                        length 1..255;
                    }
                }

                leaf action_type {
                    description "Type of forwarding action to apply.";
                    type string {
                        pattern "none|maprouting|direct|staticencap|appliance|4to6|mapdecap|decap|drop";
                    }
                }

                leaf encap_type {
                    description "Tunnel encapsulation type (VXLAN or NVGRE).";
                    type string {
                        pattern "vxlan|nvgre";
                    }
                }

                leaf vni {
                    description "VNI to use for tunnel encapsulation.";
                    type  uint32 {
                        range 1..16777215;
                    }
                }

            } /* end of list DASH_ROUTING_TYPE_LIST */
        } /* end of container DASH_ROUTING_TYPE */

        container DASH_ROUTE_TABLE {
            description "DASH LPM route table for outbound routing per ENI.";

            list DASH_ROUTE_TABLE_LIST {
                key "eni prefix";

                leaf eni {
                    description "Reference to the ENI this route applies to.";
                    type leafref {
                        path /dash:sonic-dash/dash:DASH_ENI/dash:DASH_ENI_LIST/dash:name;
                    }
                }

                leaf prefix {
                     description "Destination IP prefix for LPM lookup.";
                     type stypes:sonic-ip-prefix;
                }

                leaf action_type {
                    description "Routing type that determines the forwarding action.";
                    type leafref {
                        path /dash:sonic-dash/dash:DASH_ROUTING_TYPE/dash:DASH_ROUTING_TYPE_LIST/dash:name;
                    }
                }

                leaf vnet {
                    description "Target virtual network for vnet or vnet_direct routing.";
                    when "((current()/../action_type = 'vnet') or (current()/../action_type = 'vnet_direct'))";
                    type leafref {
                        path /dash:sonic-dash/dash:DASH_VNET/dash:DASH_VNET_LIST/dash:name;
                    }
                }

                leaf appliance {
                    description "Target appliance for appliance routing.";
                    when "(current()/../action_type = 'appliance')";
                    type leafref {
                        path /dash:sonic-dash/dash:DASH_APPLIANCE/dash:DASH_APPLIANCE_LIST/dash:name;
                    }
                }

                leaf overlay_ip {
                    when "((current()/../action_type = 'vnet') or (current()/../action_type = 'vnet_direct'))";
                    description "Overlay IP to use for mapping lookup, if routing_type is vnet_direct";
                    type inet:ip-address;
                }

                leaf overlay_sip {
                    when "(current()/../action_type = 'servicetunnel')";
                    description "Overlay src ip for service tunnel";
                    type inet:ip-address;
                }

                leaf overlay_dip {
                    when "(current()/../action_type = 'servicetunnel')";
                    description "Overlay dst ip for service tunnel";
                    type inet:ip-address;
                }

                leaf underlay_sip {
                    when "(current()/../action_type = 'servicetunnel')";
                    description "Underlay src ip for service tunnel";
                    type inet:ip-address;
                }

                leaf underlay_dip{
                    when "(current()/../action_type = 'servicetunnel')";
                    description "Underlay dst ip for service tunnel";
                    type inet:ip-address;
                }

            } /* end of list DASH_ROUTE_TABLE_LIST */
        } /* end of container DASH_ROUTE_TABLE */

        container DASH_VNET_MAPPING_TABLE {
            description "DASH CA-to-PA mapping table for a virtual network.";

            list DASH_VNET_MAPPING_TABLE_LIST {
                key "vnet ip_addr";

                leaf vnet {
                    description "Reference to the virtual network this mapping belongs to.";
                    type leafref {
                        path /dash:sonic-dash/dash:DASH_VNET/dash:DASH_VNET_LIST/dash:name;
                    }
                }

                leaf ip_addr {
                     description "Overlay CA address";
                     type inet:ip-address;
                }

                leaf routing_type {
                    description "Routing type for this mapping entry.";
                    type leafref {
                        path /dash:sonic-dash/dash:DASH_ROUTING_TYPE/dash:DASH_ROUTING_TYPE_LIST/dash:name;
                    }
                }

                leaf underlay_ip {
                     description "PA address";
                     type inet:ip-address;
                }

                leaf mac_address {
                    description "Inner destination MAC for the mapped endpoint.";
                    type yang:mac-address;
                }

                leaf use_dst_vni {
                    type boolean;
                    default false;
                    description "If set to true, use destination VNET VNI for encap";
                }

            } /* end of list DASH_MAPPING_TABLE_LIST */
        } /* end of container DASH_MAPPING_TABLE */

    } /* end of container sonic-dash */
} /* end of module sonic-dash */
