module sonic-heartbeat {

    yang-version 1.1;

    namespace "http://github.com/sonic-net/sonic-heartbeat";
    prefix heartbeat;

    organization
        "SONiC";

    contact
        "SONiC";

    description "HEARTBEAT configuration";

    revision 2025-01-09 {
        description "First Revision";
    }

    container sonic-heartbeat {

        container HEARTBEAT {
            description "Heartbeat monitoring configuration for system processes";

            list HEARTBEAT_LIST {
                key "name";

                leaf name {
                    description "process name in HEARTBEAT table";
                    type string {
                        length 1..32;
                    }
                }

                leaf heartbeat_interval {
                    description "Heartbeat interval in millisecond";
                    type uint32;
                    default "10000";
                }

                leaf alert_interval {
                    description "Alert interval in millisecond";
                    type uint32;
                    default "60000";
                }
            }
        }
    }
}
