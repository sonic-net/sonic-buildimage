module sonic-bgp-internal-neighbor {
    namespace "http://github.com/sonic-net/sonic-bgp-internal-neighbor";
    prefix bgpintnbr;
    yang-version 1.1;

    import ietf-inet-types {
        prefix inet;
    }

    import sonic-device_metadata {
        prefix dm;
    }

    import sonic-bgp-common {
        prefix bgpcmn;
    }

    import sonic-port {
        prefix port;
    }

    import sonic-portchannel {
        prefix lag;
    }

    organization
        "SONiC";

    contact
        "SONiC";

    description
        "BGP Internal Neighbor for multi asic platforms";

    revision 2021-04-10 {
        description
            "Initial revision.";
    }

    container sonic-bgp-internal-neighbor {
        container BGP_INTERNAL_NEIGHBOR {
            list BGP_INTERNAL_NEIGHBOR_LIST {
                description "List for internal neighbors in multi asic platforms";
                key "neighbor";

                must "local_addr or starts-with(neighbor, 'Eth') or starts-with(neighbor, 'Po') or starts-with(neighbor, 'Vlan')" {
                    error-message "Mandatory local_addr is missing for numbered neighbor";
                }

                leaf neighbor {
                    type union {
                        type inet:ip-address;
                        type leafref {
                            path "/port:sonic-port/port:PORT/port:PORT_LIST/port:name";
                        }
                        type leafref {
                            path "/lag:sonic-portchannel/lag:PORTCHANNEL/lag:PORTCHANNEL_LIST/lag:name";
                        }
                        type string {
                            pattern 'Vlan([0-9]{1,3}|[1-3][0-9]{3}|[4][0][0-8][0-9]|[4][0][9][0-4])';
                        }
                        type string {
                            pattern '(Ethernet|Eth|PortChannel|Po)[0-9]+\.[0-9]+';
                        }
                    }
                    description "BGP Neighbor address or interface name";
                }
                uses bgpcmn:sonic-bgp-cmn-neigh {
                    refine asn {
                        must "(current() = /dm:sonic-device_metadata/dm:DEVICE_METADATA/dm:localhost/dm:bgp_asn)" {
                            error-message "Internal iBGP neighbors should have same ASN as defined in device metadata";
                        }
                        must ". >= 1" {
                            error-message "ASN must be greater than 0";
                        }
                    }
                    refine local_addr {
                        must "(starts-with(../neighbor, 'Eth') or starts-with(../neighbor, 'Po') or starts-with(../neighbor, 'Vlan') or
                                (contains(../neighbor, '.') and contains(current(), '.')) or
                                (contains(../neighbor, ':') and contains(current(), ':')))" {
                            error-message "local address and neighbor address family does not match";
                        }
                    }
                }
            }
        }
    }
}
