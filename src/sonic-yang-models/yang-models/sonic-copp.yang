module sonic-copp {

	yang-version 1.1;

	namespace "http://github.com/sonic-net/sonic-copp";
	prefix copp;

	import sonic-types {
		prefix stypes;
	}

	import sonic-port {
		prefix port;
	}

	description "CoPP YANG Module for SONiC OS";

	revision 2026-11-08 {
		description "Add COPP_TRAP_EXCLUDE_PORTS";
	}

	revision 2021-03-31 {
		description
			"First Revision";
	}

	container sonic-copp {
		container COPP_GROUP {

			description "Configures Control Plane Policing groups that rate-limit traffic destined to the CPU.";

			list COPP_GROUP_LIST {

				description "A named CoPP group with queue, trap action, and policer settings.";
				key name;

				leaf name {
					type string;
					description "Control plane policing group name";
				}

				leaf queue {
					type uint32;
					default 0;
					description "CPU receive queue number; higher values indicate higher priority.";
				}

				leaf trap_priority {
					type uint32;
					default 0;
					description "Priority assigned to the trap; higher values are matched first.";
				}

				leaf trap_action {
					mandatory true;
					type stypes:policer_packet_action;
					description "Action applied to trapped packets (forward, drop, copy, etc.).";
				}

				leaf meter_type {
					mandatory true;
					type stypes:meter_type;
					description "Metering unit for the embedded policer (packets or bytes).";
				}

				leaf mode {
					mandatory true;
					type enumeration {
						enum sr_tcm;
						enum tr_tcm;
						enum storm;
					}
					description "Policer mode: single-rate TCM, two-rate TCM, or storm control.";
				}

				leaf color {
					type stypes:policer_color_source;
					description "Policer color awareness mode (aware or blind).";
				}

				leaf cir {
					type uint64;
					default 0;
					description
						"Committed information rate for the dual-rate token
						bucket policer.  This value represents the rate at which
						tokens are added to the primary bucket.";
				}

				leaf cbs {
					must "((current()/../cir) and (current()/../cir > 0))" {
						error-message "cbs can't be configured without cir.";
					}
					must "(current() >= current()/../cir)" {
						error-message "cbs must be greater than or equal to cir";
					}
					type uint64;
					default 0;
					description
						"Committed burst size for the dual-rate token bucket
						policer.  This value represents the depth of the token
						bucket.";
				}

				leaf pir {
					when "current()/../mode = 'tr_tcm'";
					must "((current()/../cir) and (current()/../cir > 0))" {
						error-message "pir can't be configured without cir.";
					}
					must "(current() >= current()/../cir)" {
						error-message "pir must be greater than or equal to cir";
					}
					type uint64;
					description
						"Peak information rate for the dual-rate token bucket
						policer.  This value represents the rate at which tokens
						are added to the secondary bucket.";
				}

				leaf pbs {
					when "((current()/../mode = 'sr_tcm') or (current()/../mode = 'tr_tcm'))";
					must "((not(current()/../cbs)) or (current() >= current()/../cbs))" {
						error-message "pbs must be greater than or equal to cbs";
					}
					type uint64;
					description
						"Excess burst size for the dual-rate token bucket policer.
						This value represents the depth of the secondary bucket.";
				}

				leaf green_action {
					type stypes:policer_packet_action;
					default "forward";
					description "Action for packets classified as green by the policer.";
				}

				leaf yellow_action {
					when "((current()/../mode = 'sr_tcm') or (current()/../mode = 'tr_tcm'))";
					type stypes:policer_packet_action;
					default "forward";
					description "Action for packets classified as yellow by the policer.";
				}

				leaf red_action {
					type stypes:policer_packet_action;
					default "forward";
					description "Action for packets classified as red by the policer.";
				}
			}
			/* end of list COPP_GROUP_LIST */
		}
		/* end of container COPP_GROUP */

		container COPP_TRAP {

			description "Configures CoPP trap entries that bind trap IDs to CoPP groups.";

			list COPP_TRAP_LIST {

				description "A named CoPP trap binding trap IDs to a policing group.";
				key name;

				leaf name {
					type string;
					description "Control plane policing trap name";
				}

				leaf trap_ids {
					mandatory true;
					type string;
					description "Comma-separated list of trap identifiers bound to this entry.";
				}

				leaf trap_group {
					type leafref {
						path "/sonic-copp/COPP_GROUP/COPP_GROUP_LIST/name";
					}
					description "Reference to the CoPP group that polices these traps.";
				}

				leaf always_enabled {
					type boolean;
					description "When true, the trap is always installed regardless of feature enablement.";
				}
			}
			/* end of list COPP_TRAP_LIST */
		}
		/* end of container COPP_TRAP */

		container COPP_TRAP_EXCLUDE_PORTS {
			description "Ports excluded from all CoPP traps, including ttl_error.
				Physical ports only. PortChannel members are skipped.";

			container GLOBAL {
				leaf-list ports {
					type leafref {
						path /port:sonic-port/port:PORT/port:PORT_LIST/port:name;
					}
				}
			}
			/* end of container GLOBAL */
		}
		/* end of container COPP_TRAP_EXCLUDE_PORTS */
	}
	/* end of top level container */

	rpc get-match-protocols {
		description
			"RPC to get allowed match protocols";

		output {
			list Match_protocols {
				key "Protocol";

				leaf Protocol {
					type string;
					description
						"Protocol name";
				}
			}
		}
	}
	/* end of rpc get-match-protocols */
}
/* end of module sonic-copp */
