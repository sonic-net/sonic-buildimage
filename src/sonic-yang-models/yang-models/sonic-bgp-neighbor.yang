module sonic-bgp-neighbor {
    namespace "http://github.com/sonic-net/sonic-bgp-neighbor";
    prefix bgpnbr;
    yang-version 1.1;

    import ietf-inet-types {
        prefix inet;
    }

    import sonic-bgp-common {
        prefix bgpcmn;
    }

    import sonic-port {
        prefix port;
    }

    import sonic-portchannel {
        prefix lag;
    }

    // Comment sonic-vlan import here until libyang back-links issue is resolved for VLAN leaf reference.
    //import sonic-vlan {
    //    prefix vlan;
    //}

    import sonic-bgp-global {
        prefix bgpg;
    }

    import sonic-bgp-peergroup {
        prefix bgppg;
    }

    import sonic-vnet {
        prefix svnet;
    }

    import sonic-device_metadata {
        prefix sdm;
    }

    organization
        "SONiC";

    contact
        "SONiC";

    description
        "SONIC BGP Neighbor";

    revision 2026-11-13 {
        description
            "Require an asn on both BGP neighbor lists, since a neighbor without one establishes no
             session. On BGP_NEIGHBOR_LIST it may be omitted only when frr_mgmt_framework_config is
             true and the neighbor has a peer_group_name or is attached to an interface. A neighbor
             that validated before this revision may now be rejected.";
    }

    revision 2026-07-22 {
        description
            "Add VNet name support to BGP_NEIGHBOR_LIST and BGP_NEIGHBOR_AF_LIST vrf_name leaf.";
    }

    revision 2021-02-26 {
        description
            "Initial revision.";
    }

    container sonic-bgp-neighbor {
        container BGP_NEIGHBOR {
            // Rows on this list are keyed on the neighbor alone and are consumed only by bgpcfgd;
            // frrcfgd skips a single-key BGP_NEIGHBOR row outright. bgpcfgd renders the peer's
            // remote-as from asn alone -- neither the PEER_V4/PEER_V6 peer-group nor DEVICE_METADATA
            // supplies one -- so a row with no asn hands FRR a remote-as with no value and the whole
            // neighbor is rejected. Hence the must below.
            list BGP_NEIGHBOR_TEMPLATE_LIST {
                description "This list is to support template based BGP neighbor configuration.";
                key "neighbor";

                must "boolean(asn)" {
                    error-message "A template based BGP neighbor must carry an asn.";
                }

                leaf neighbor {
                    type union {
                        type inet:ip-address;
                        type leafref {
                            path "/port:sonic-port/port:PORT/port:PORT_LIST/port:name";
                        }
                        type leafref {
                            path "/lag:sonic-portchannel/lag:PORTCHANNEL/lag:PORTCHANNEL_LIST/lag:name";
                        }
                        type string {
                            pattern 'Vlan([0-9]{1,3}|[1-3][0-9]{3}|[4][0][0-8][0-9]|[4][0][9][0-4])';
                        }
                        type string {
                            pattern '(Ethernet|Eth|PortChannel|Po)[0-9]+\.[0-9]+';
                        }
                    }
                    description "BGP Neighbor address or interface name";
                }

                uses bgpcmn:sonic-bgp-cmn-neigh {
                    refine asn {
                        must ". >= 1" {
                            error-message "ASN must be greater than 0";
                        }
                    }
                }
            }

            // Rows on this list are keyed on vrf_name and neighbor, and both BGP configuration
            // daemons consume them: frrcfgd, which requires frr_mgmt_framework_config to be true in
            // DEVICE_METADATA and reads no other neighbor list, and bgpcfgd, which reads this list
            // and BGP_NEIGHBOR_TEMPLATE_LIST alike. Only one of the two runs on a given device.
            // A row with no asn fails differently under each and is silent in both: frrcfgd emits
            // nothing at all for it, while bgpcfgd renders the peer's remote-as from asn alone --
            // never from peer_group_name -- and hands FRR a remote-as with no value. Hence the must
            // below, and why its exemptions are scoped to frrcfgd.
            // The mode test anchors on hostname, not on the localhost container and not on
            // frr_mgmt_framework_config itself: localhost is a non-presence container holding
            // leaves with defaults, so libyang materialises it -- and a "false" for the mode --
            // before any must is evaluated, which makes not(localhost) and a not() on the mode leaf
            // both dead. hostname has no default, so its absence is what actually says
            // DEVICE_METADATA was never supplied and the tree is a subset. (A when statement is
            // evaluated before defaults are added and can test the container; a must cannot.)
            list BGP_NEIGHBOR_LIST {
                description "This list is to support generic BGP neighbor configuration.";
                key "vrf_name neighbor";

                must "boolean(asn) or
                      ((not(/sdm:sonic-device_metadata/sdm:DEVICE_METADATA/sdm:localhost/sdm:hostname) or
                        /sdm:sonic-device_metadata/sdm:DEVICE_METADATA/sdm:localhost/sdm:frr_mgmt_framework_config = 'true')
                       and (boolean(peer_group_name) or
                            starts-with(neighbor, 'Eth') or starts-with(neighbor, 'Po') or
                            starts-with(neighbor, 'Vlan')))" {
                    error-message "A BGP neighbor must carry an asn.";
                }

                leaf vrf_name {
                    type union {
                        type leafref {
                            path "/bgpg:sonic-bgp-global/bgpg:BGP_GLOBALS/bgpg:BGP_GLOBALS_LIST/bgpg:vrf_name";
                        }
                        type leafref {
                            path "/svnet:sonic-vnet/svnet:VNET/svnet:VNET_LIST/svnet:name";
                        }
                    }
                    description "Network-instance/VRF name or VNet name";
                }

                leaf neighbor {
                    type union {
                        type inet:ip-address;
                        type leafref {
                            path "/port:sonic-port/port:PORT/port:PORT_LIST/port:name";
                        }
                        type leafref {
                            path "/lag:sonic-portchannel/lag:PORTCHANNEL/lag:PORTCHANNEL_LIST/lag:name";
                        }
                       // Comment VLAN leaf reference here until libyang back-links issue is resolved and use VLAN string pattern
                       // type leafref {
                       //     path "/vlan:sonic-vlan/vlan:VLAN/vlan:VLAN_LIST/vlan:name";
                       // }
                        type string {
                            pattern 'Vlan([0-9]{1,3}|[1-3][0-9]{3}|[4][0][0-8][0-9]|[4][0][9][0-4])';
                        }
                        type string {
                            pattern '(Ethernet|Eth|PortChannel|Po)[0-9]+\.[0-9]+';
                        }
                    }
                    description "BGP Neighbor, it will be neighbor address or interface name";
                }

                leaf peer_group_name {
                    type leafref {
                        path "/bgppg:sonic-bgp-peergroup/bgppg:BGP_PEER_GROUP/bgppg:BGP_PEER_GROUP_LIST[bgppg:vrf_name=current()/../vrf_name]/bgppg:peer_group_name";
                    }
                    description "Peer group name";
                }

                uses bgpcmn:sonic-bgp-cmn;
            }
        }

        container BGP_NEIGHBOR_AF {
            list BGP_NEIGHBOR_AF_LIST {
                key "vrf_name neighbor afi_safi";

                leaf vrf_name {
                    type union {
                        type leafref {
                            path "/bgpg:sonic-bgp-global/bgpg:BGP_GLOBALS/bgpg:BGP_GLOBALS_LIST/bgpg:vrf_name";
                        }
                        type leafref {
                            path "/svnet:sonic-vnet/svnet:VNET/svnet:VNET_LIST/svnet:name";
                        }
                    }
                    description "Network-instance/VRF name or VNet name";
                }

                leaf neighbor {
                    type leafref {
                        path "../../../BGP_NEIGHBOR/BGP_NEIGHBOR_LIST[vrf_name=current()/../vrf_name]/neighbor";
                    }
                    description "BGP Neighbor, it will be neighbor address or interface name";
                }
                uses bgpcmn:sonic-bgp-cmn-af;
            }
        }
    }
}
