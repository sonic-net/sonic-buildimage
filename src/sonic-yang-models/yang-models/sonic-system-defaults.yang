module sonic-system-defaults{

    yang-version 1.1;

    namespace "http://github.com/Azure/system-defaults";
    prefix system-defaults;

    import sonic-types {
        prefix stypes;
    }

    description "System-wide default feature settings YANG module for SONiC OS.";

    revision 2026-06-02 {
        description "Documented swss_zmq and async_rec as SYSTEM_DEFAULTS list entries.";
    }

    container sonic-system-defaults {

        container SYSTEM_DEFAULTS {

            description "Default enable/disable state for optional system features.";

            list SYSTEM_DEFAULTS_LIST {

                key "name";
                description "A system default entry keyed by feature name.";

                leaf name {
                    description "Name of the system feature.";
                    type string {
                        length 1..32;
                    }
                }

                leaf status {
                    description "Default administrative state of the feature (enabled or disabled).";
                    type stypes:admin_mode;
                }

            }

        }
    }
}
