module sonic-dscp-fc-map {

    yang-version 1.1;

    namespace "http://github.com/sonic-net/sonic-dscp-fc-map";

    prefix dtm;

    organization
        "SONiC";

    contact
        "SONiC";

    description
        "DSCP_TO_FC_MAP yang Module for SONiC OS";

    revision 2021-10-29 {
        description
            "Initial revision.";
    }

    container sonic-dscp-fc-map {

        container DSCP_TO_FC_MAP {

            description "Maps DSCP values to forwarding class for Class-Based Forwarding.";

            list DSCP_TO_FC_MAP_LIST {

                key "name";

                description "A named DSCP to forwarding class map.";

                leaf name {
                    type string {
                        pattern '[a-zA-Z0-9]{1}([-a-zA-Z0-9_]{0,31})';
                        length 1..32 {
                            error-message "Invalid length for map name.";
                            error-app-tag map-name-invalid-length;
                        }
                    }
                    description "Name of the DSCP to FC map.";
                }

                list DSCP_TO_FC_MAP {

                    key "dscp";

                    description "Single mapping entry from a DSCP value to a forwarding class.";

                    leaf dscp {
                        type string {
                            pattern "6[0-3]|[1-5][0-9]?|[0-9]?" {
                                error-message "Invalid DSCP";
                                error-app-tag dscp-invalid;
                            }
                        }
                        description "DSCP value (0-63).";
                    }

                    leaf fc {
                        type string {
                            pattern "[0-7]?" {
                                error-message "Invalid Forwarding Class";
                                error-app-tag fc-invalid;
                            }
                        }
                        description "Target forwarding class (0-7) for Class-Based Forwarding.";
                    }
                }
            }
        }
    }
}
