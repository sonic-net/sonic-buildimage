module sonic-breakout_cfg {

    yang-version 1.1;

    namespace "http://github.com/sonic-net/sonic-breakout_cfg";
    prefix breakout_cfg;

    description "BREAKOUT_CFG YANG Module for SONiC OS";

    revision 2020-04-10 {
        description "First Revision";
    }

    container sonic-breakout_cfg {

        container BREAKOUT_CFG {

            description "Port breakout mode configuration for dynamic port splitting";

            list BREAKOUT_CFG_LIST {

                key "port";

                /*
                 * This is leaf instead of a leafref towards port, because this
                 * table will contains Parent ports and their current breakout-mode,
                 * irrespective of port is present in PORT table or not. Specially
                 * during Dynamic Port Breakout, Parent Port may not be present in
                 * PORT table.
                 */
                leaf port {
                    description "Parent port name for breakout configuration";
                    type string {
                        length 1..255;
                    }
                }

                leaf brkout_mode {
                    description "break_mode for port, it is verifed using platform.json";
                    type string {
                        length 1..64;
                    }
                }
            }
            /* end of list BREAKOUT_CFG_LIST */
        }
        /* end of container BREAKOUT_CFG */
    }
    /* end of top level container */
}
/* end of module sonic-breakout_cfg */
