module sonic-vrf {
    namespace "http://github.com/sonic-net/sonic-vrf";
    prefix vrf;

    import sonic-types {
        prefix stypes;
    }

    organization
        "SONiC";

    contact
        "SONiC";

    description
        "Virtual Routing and Forwarding (VRF) instance configuration for L3 traffic isolation";

    revision 2021-03-30 {
        description
            "Initial revision.";
    }

    container sonic-vrf {
        container VRF {
            description "VRF instance configuration table";

            list VRF_LIST {
                description "Configuration entry for a Virtual Routing and Forwarding instance";

                key "name";

                leaf name {
                    description "VRF instance name (e.g. Vrf_blue) or the reserved default VRF name";
                    type stypes:interface_name {
                        pattern "Vrf[a-zA-Z0-9_-]+|default" {
                            error-message "Invalid VRF name";
                            error-app-tag vrf-name-invalid;
                        }
                    }
                }

                leaf fallback {
                    type  boolean;
                    default false;
                    description
                        "Enable/disable fallback feature which is useful for specified VRF user to access internet through global/main route.";
                }

                leaf vni {
                    type uint32 {
                        range "0..16777215";
                    }
                    default 0;
                    description
                        "VNI mapped to VRF";
                }

                leaf description {
                    type string {
                        length "1..255";
                    }
                    description
                        "Description for the VRF";
                }
            } /* end of list VRF_LISt */
        } /* end of container VRf */
    } /* end of container sonic-vrf */
}/* end of module sonic-vrf */
