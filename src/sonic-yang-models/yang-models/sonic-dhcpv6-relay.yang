module sonic-dhcpv6-relay {

	namespace "http://github.com/sonic-net/sonic-dhcpv6-relay";

	prefix sdhcpv6relay;

	yang-version 1.1;

	import ietf-inet-types {
		prefix inet;
	}

	organization "SONiC";

	contact "SONiC";

	description "DHCPv6 Relay yang Module for SONiC OS";

	revision 2026-06-30 {
		description "Add server_vrf to reach DHCPv6 servers in a non-default VRF";
	}

	revision 2021-10-30 {
		description "First Revision";
	}

	container sonic-dhcpv6-relay {

		container DHCP_RELAY {

			description "DHCPv6 relay agent configuration per VLAN interface";

			list DHCP_RELAY_LIST {

				key "name";

				leaf name {
					description "VLAN interface name for DHCPv6 relay";
					type string;
				}

				leaf-list dhcpv6_servers {
					description "Configure the dhcp v6 servers";
					type inet:ipv6-address;
					ordered-by user;
				}

				leaf rfc6939_support {
					description "Set rfc6939 for the relay";
					type string {
						pattern "false|true";
					}
				}

				leaf interface_id {
					description "Enable interface ID insertion in relayed messages";
					type string {
						pattern "false|true";
					}
				}

				leaf server_vrf {
					description "Name of the VRF in which the configured DHCPv6 servers are reachable, used to bind the relay's upstream socket (SO_BINDTODEVICE) so relay-forward egresses in that VRF. Set this only when the servers are in a different VRF than the VLAN interface's own VRF; when unset the servers are reached in the VLAN's VRF. May name a data VRF, the management VRF, or 'default' (global routing table). Not modelled as a leafref because 'default' and the management VRF are valid targets that do not appear in the VRF table.";
					type string {
						length "1..15";
					}
				}
			}
			/* end of VLAN_LIST */
		}
		/* end of container DHCP_RELAY */
	}
	/* end of container sonic-dhcpv6-relay */
}
/* end of module sonic-dhcpv6-relay */
