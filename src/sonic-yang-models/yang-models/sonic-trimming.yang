module sonic-trimming {

    yang-version 1.1;

    namespace "http://github.com/sonic-net/sonic-trimming";
    prefix trim;

    description "TRIMMING configuration";

    revision 2024-11-01 {
        description "First Revision";
    }

    container sonic-trimming {

        container SWITCH_TRIMMING {

            description "Global packet trimming settings for congestion telemetry.";

            container GLOBAL {

                description "System-wide packet trimming configuration.";

                leaf size {
                    description "Size (in bytes) to trim eligible packet";
                    type uint32;
                }

                leaf dscp_value {
                    description
                        "DSCP value assigned to a packet after trimming.
                        When set to from-tc, the tc_value is used for mapping to the DSCP";
                    type union {
                        type uint8 {
                            range "0..63" {
                                error-message "Invalid DSCP value";
                                error-app-tag dscp-invalid;
                            }
                        }
                        type string {
                            pattern "from-tc";
                        }
                    }
                }

                leaf tc_value {
                    description "TC value assigned to a packet after trimming";
                    type uint8;
                }

                leaf queue_index {
                    description
                        "Queue index to use for transmission of a packet after trimming.
                        When set to dynamic, the dscp_value is used for mapping to the queue";
                    type union {
                        type uint8;
                        type string {
                            pattern "dynamic";
                        }
                    }
                }

            }
            /* end of container GLOBAL */
        }
        /* end of container SWITCH_TRIMMING */
    }
    /* end of container sonic-trimming */
}
/* end of module sonic-trimming */
