module sonic-bgp-device-global {
    namespace "http://github.com/sonic-net/sonic-bgp-device-global";
    prefix bgp_device_global;
    yang-version 1.1;

    import sonic-srv6 {
        prefix srv6;
    }

    import sonic-bgp-prefix-list {
        prefix bgppl;
    }

    organization
        "SONiC";

    contact
        "SONiC";

    description
        "SONIC Device-specific BGP global data";

    revision 2026-11-14 {
        description "Add BGP SRv6 GRT configuration.";
    }

    revision 2026-04-28 {
        description "Add chassis_tsa_supported to select CHASSIS_APP_DB vs per-linecard TSA orchestration";
    }

    revision 2024-01-28 {
        description "Add Weighted ECMP using BGP link bandwidth";
    }

    revision 2022-06-26 {
        description "Initial revision";
    }

    container sonic-bgp-device-global {

        container BGP_DEVICE_GLOBAL {

            description "Device-level BGP settings such as TSA, WCMP, IDF isolation, and SRv6.";

            container STATE {

                description "BGP device-specific global data";

                leaf tsa_enabled {
                    type boolean;
                    default "false";
                    description
                    "When set to true, Traffic is shifted away (TSA), i.e, BGP routes are not advertised to neighboring routers";
                }

                leaf chassis_tsa_supported {
                    type boolean;
                    default "false";
                    description
                    "When true, chassis-wide TSA state is synchronized using CHASSIS_APP_DB on the supervisor.
                     When false (default), CHASSIS_APP_DB is not used for TSA, the supervisor should push TSA/TSB
                     to linecards out-of-band (for example via rexec).";
                }

                leaf wcmp_enabled {
                    description "Enables/Disables Weighted-Equal Cost-Multipath using BGP link bandwidth";
                    type boolean;
                    default "false";
                }

                leaf idf_isolation_state {
                    description "Configures device IDF isolation state";
                    type enumeration {
                        enum isolated_no_export {
                            description "IDF isolated using no-export community tag";
                        }
                        enum isolated_withdraw_all {
                            description "IDF isolated by withdrawing routes";
                        }
                        enum unisolated {
                            description "IDF un-isolated";
                        }
                    }
                    default "unisolated";
                }

            }
            /* end of STATE container */
            /* start of CONFED container */
            container CONFED
            {
                description "BGP Confederation related configuration";

                leaf asn {
                    type uint32 {
                        range "1..4294967295";
                    }
                    description "Autonomous System Number for BGP confederation";
                }

                /* List of peer ASN part of the confederation */
                leaf peers {
                    type string;
                    description "List of sub-ASNs in the confederation separated by semi-colon";
                }
            }
            /* end of CONFED container */

            container SRV6 {
                description "BGP SRv6 locator and GRT Service SID advertisement configuration.";

                leaf bgp_srv6_locator {
                    type leafref {
                        path "/srv6:sonic-srv6/srv6:SRV6_MY_LOCATORS/srv6:SRV6_MY_LOCATORS_LIST/srv6:locator_name";
                    }
                    description "SRv6 locator used to allocate BGP Service SIDs.";
                }

                leaf bgp_srv6_ipv4_sid_advertise {
                    type boolean;
                    default false;
                    description "Enable Service SID advertisement for eligible IPv4 GRT routes.";
                }

                leaf bgp_srv6_ipv4_sid_prefix_list {
                    type leafref {
                        path "/bgppl:sonic-bgp-prefix-list/bgppl:PREFIX_LIST/bgppl:PREFIX_LIST_LIST/bgppl:prefix_type";
                    }
                    description "Optional IPv4 prefix list used to select GRT routes for SID advertisement.";
                }

                leaf bgp_srv6_ipv6_sid_advertise {
                    type boolean;
                    default false;
                    description "Enable Service SID advertisement for eligible IPv6 GRT routes.";
                }

                leaf bgp_srv6_ipv6_sid_prefix_list {
                    type leafref {
                        path "/bgppl:sonic-bgp-prefix-list/bgppl:PREFIX_LIST/bgppl:PREFIX_LIST_LIST/bgppl:prefix_type";
                    }
                    description "Optional IPv6 prefix list used to select GRT routes for SID advertisement.";
                }
            }
            /* end of SRV6 container */
        }
        /* end of BGP_DEVICE_GLOBAL container */
    }
    /* end of container sonic-bgp-device-global */
}
/* end of module sonic-bgp-device-global */
