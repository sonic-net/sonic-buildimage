module sonic-tc-priority-group-map {

    yang-version 1.1;

    namespace "http://github.com/sonic-net/sonic-tc-priority-group-map";

    prefix tpgm;

    import sonic-types {
        prefix stypes;
    }

    organization
        "SONiC";

    contact
        "SONiC";

    description
        "TC_TO_PRIORITY_GROUP_MAP yang Module for SONiC OS";

    revision 2021-04-15 {
        description
            "Initial revision.";
    }

    container sonic-tc-priority-group-map {

        container TC_TO_PRIORITY_GROUP_MAP {

            description "Maps traffic class to ingress priority group for buffer admission control.";

            list TC_TO_PRIORITY_GROUP_MAP_LIST {

                key "name";

                description "A named traffic class to priority group map.";

                leaf name {
                    type string {
                        pattern '[a-zA-Z0-9]{1}([-a-zA-Z0-9_]{0,31})';
                        length 1..32 {
                            error-message "Invalid length for map name.";
                            error-app-tag map-name-invalid-length;
                        }
                    }
                    description "Name of the TC to priority group map.";
                }

                list TC_TO_PRIORITY_GROUP_MAP {

                    key "tc";

                    description "Single mapping entry from a traffic class to an ingress priority group.";

                    leaf tc {
                        type stypes:tc_type;
                        description "Source traffic class.";
                    }

                    leaf pg {
                        type string {
                            pattern "[0-7]?" {
                                error-message "Invalid Priority Group";
                                error-app-tag pg-invalid;
                            }
                        }
                        description "Target ingress priority group (0-7).";
                    }
                }
            }
        }
    }
}
