module sonic-ntp {

    yang-version 1.1;

    namespace "http://github.com/sonic-net/sonic-system-ntp";
    prefix ntp;

    import ietf-inet-types {
        prefix inet;
    }

    import sonic-port {
        prefix port;
    }

    import sonic-mgmt_vrf {
        prefix mvrf;
    }

    import sonic-portchannel {
        prefix lag;
    }
    /* comment out sonic-vlan until related build issue is fixed
    import sonic-vlan {
        prefix vlan;
    }
    */
    import sonic-loopback-interface {
        prefix lo;
    }

    import sonic-mgmt_port {
        prefix mprt;
    }

    import sonic-types {
        prefix stypes;
    }

    description
        "Network Time Protocol (NTP) client configuration";

    revision 2021-04-07 {
        description
            "First revision";
    }

    revision 2023-03-20 {
        description
            "Add extended configuration options";
    }

    revision 2025-07-21 {
        description
            "Corrected NTP_KEY_LIST list name";
    }

    typedef association-type {
        description "NTP server association type";
        type enumeration {
            enum server;
            enum pool;
        }
    }

    typedef key-type {
        description "NTP key encryption type";
        type enumeration {
            enum md5;
            enum sha1;
            enum sha256;
            enum sha384;
            enum sha512;
        }
    }

    typedef key-id {
        description "NTP key ID";
        type uint16 {
            range 1..65535 {
                error-message "Failed NTP key ID";
            }
        }
    }

    container sonic-ntp {

        container NTP {
            description "NTP global configuration container.";

            container global {

                description "Global NTP client settings.";

                leaf-list src_intf {
                    type union {
                        type leafref {
                            path /port:sonic-port/port:PORT/port:PORT_LIST/port:name;
                        }
                        type leafref {
                            path /lag:sonic-portchannel/lag:PORTCHANNEL/lag:PORTCHANNEL_LIST/lag:name;
                        }
                        /*
                        type leafref {
                            path /vlan:sonic-vlan/vlan:VLAN/vlan:VLAN_LIST/vlan:name;
                        }
                        */
                        type leafref {
                            path /lo:sonic-loopback-interface/lo:LOOPBACK_INTERFACE/lo:LOOPBACK_INTERFACE_LIST/lo:name;
                        }
                        type leafref {
                            path /mprt:sonic-mgmt_port/mprt:MGMT_PORT/mprt:MGMT_PORT_LIST/mprt:name;
                        }
                        type string {
                            pattern 'eth0';
                        }
                    }
                    ordered-by user;
                    description
                        "This is the interface whose IP address is used as the source IP address for
                         generating NTP traffic. User is required to make sure that the NTP server
                         is reachable via this IP address and the same IP address is reachable
                         from the NTP server. The source interface should be in the same VRF as the
                         VRF NTP is enabled in.";
                }

                leaf vrf {
                    must "(current() != 'mgmt') or (/mvrf:sonic-mgmt_vrf/mvrf:MGMT_VRF_CONFIG/mvrf:vrf_global/mvrf:mgmtVrfEnabled = 'true')" {
                        error-message "Must condition not satisfied. Try enable Management VRF.";
                    }

                    type string {
                        pattern "mgmt|default";
                    }

                    description
                        "NTP can be enabled only in one VRF at a time. In this revision, it is either
                         default VRF or Management VRF.";
                }

                leaf authentication {
                    type stypes:admin_mode;
                    default disabled;
                    description "NTP authentication state";
                }

                leaf dhcp {
                    type stypes:admin_mode;
                    default enabled;
                    description "Use NTP servers distributed by DHCP";
                }

                leaf server_role {
                    type stypes:admin_mode;
                    default enabled;
                    description "NTP server functionality state";
                }

                leaf admin_state {
                    type stypes:admin_mode;
                    default enabled;
                    description "NTP feature state";
                }

            } /* end of container global */

        } /* end of container NTP */

        container NTP_SERVER {

            description "NTP upstream server and pool configuration.";

            list NTP_SERVER_LIST {
                description
                    "List of all upstream servers to use.";

                key "server_address";

                leaf server_address {
                    type inet:host;
                    description "Hostname or IP address of the NTP server or pool.";
                }

                leaf association_type {
                    type association-type;
                    default server;
                    description "NTP remote association type: server or pool.";
                }

                leaf iburst {
                    type stypes:on-off;
                    default on;
                    description "NTP aggressive polling";
                }

                leaf key {
                    description "NTP server key ID";
                    type leafref {
                        path /ntp:sonic-ntp/ntp:NTP_KEY/ntp:NTP_KEY_LIST/ntp:id;
                    }
                }

                leaf resolve_as {
                    type inet:host;
                    description "Server resolved IP address";
                }

                leaf admin_state {
                    type stypes:admin_mode;
                    default enabled;
                    description "NTP server state";
                }

                leaf trusted {
                    type stypes:yes-no;
                    default no;
                    description "Trust this server. It will force time
                                 synchronization only to this server when
                                 authentication is enabled";
                }

                leaf version {
                    type uint8 {
                        range "3..4" {
                            error-message "Failed NTP version";
                        }
                    }
                    default 4;
                    description "NTP proto version to communicate with NTP
                                 server";
                }

            } /* end of list NTP_SERVER_LIST */

        } /* end of container NTP_SERVER */

        container NTP_KEY {

            description "NTP authentication keys inventory";

            list NTP_KEY_LIST {
                description "NTP authentication keys inventory";
                key "id";

                leaf id {
                    type key-id;
                    description "NTP key ID";
                }

                leaf trusted {
                    type stypes:yes-no;
                    default no;
                    description "Trust this NTP key";
                }

                leaf value {
                    type string {
                        length 1..64;
                    }
                    description "NTP encrypted authentication key";
                }

                leaf type {
                    type key-type;
                    default md5;
                    description "NTP authentication key type";
                }
            } /* end of list NTP_KEY_LIST */

        } /* end of container NTP_KEY */

    } /* end of container  sonic-ntp */

} /* end of module sonic-ntp */
