module sonic-cable-length {

    yang-version 1.1;

    namespace  "http://github.com/sonic-net/sonic-cable-length";

    prefix cable-length;

    import sonic-port {
        prefix port;
    }

    description "CABLE_LENGTH configuration";

    revision 2021-11-11 {
        description "Initial version";
    }

    container sonic-cable-length {
        container CABLE_LENGTH {

            description "Cable length per port, used for lossless buffer calculation";

            list CABLE_LENGTH_LIST {
                key "name";

                leaf name {
                    description "Name of the cable length configuration group";
                    type string {
                        pattern '[a-zA-Z0-9]{1}([-a-zA-Z0-9_]{0,31})' {
                            error-message "Invalid cable length list name.";
                            error-app-tag cable-length-invalid-list-name;
                        }
                        length 1..32 {
                            error-message "Invalid length for the cable length list name.";
                            error-app-tag cable-length-invalid-list-name-length;
                        }
                    }
                }

                list CABLE_LENGTH {
                    key "port";

                    leaf port {
                        description "Port associated with this cable length entry";
                        type leafref {
                            path /port:sonic-port/port:PORT/port:PORT_LIST/port:name;
                        }
                    }

                    leaf length {
                        description "Cable length in meters (e.g., '40m')";
                        type string {
                            pattern '[0-9]+m' {
                                error-message "Invalid cable length.";
                                error-app-tag cable-length-invalid-length;
                            }
                        }
                    }
                }
            }
        }
    }
}
