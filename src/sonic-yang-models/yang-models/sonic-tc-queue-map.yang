module sonic-tc-queue-map {

    yang-version 1.1;

    namespace "http://github.com/sonic-net/sonic-tc-queue-map";

    prefix tqm;

    import sonic-types {
        prefix stypes;
    }

    organization
        "SONiC";

    contact
        "SONiC";

    description
        "TC_TO_QUEUE_MAP yang Module for SONiC OS";

    revision 2021-04-15 {
        description
            "Initial revision.";
    }

    container sonic-tc-queue-map {

        container TC_TO_QUEUE_MAP {

            description "Maps traffic class to egress queue for packet scheduling.";

            list TC_TO_QUEUE_MAP_LIST {

                key "name";

                description "A named traffic class to egress queue map.";

                leaf name {
                    type string {
                        pattern '[a-zA-Z0-9]{1}([-a-zA-Z0-9_]{0,31})';
                        length 1..32 {
                            error-message "Invalid length for map name.";
                            error-app-tag map-name-invalid-length;
                        }
                    }
                    description "Name of the TC to queue map.";
                }

                list TC_TO_QUEUE_MAP {

                    key "tc";

                    description "Single mapping entry from a traffic class to an egress queue.";

                    leaf tc {
                        type stypes:tc_type;
                        description "Source traffic class.";
                    }

                    leaf qindex {
                        type string {
                            pattern "[0-9]?" {
                                error-message "Invalid queue index";
                                error-app-tag queue-index-invalid;
                            }
                        }
                        description "Target egress queue index (0-9).";
                    }
                }
            }
        }
    }
}
