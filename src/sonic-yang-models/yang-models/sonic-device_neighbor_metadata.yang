module sonic-device_neighbor_metadata {

    yang-version 1.1;

    namespace "http://github.com/sonic-net/sonic-device_neighbor_metadata";
    prefix device_neighbor_metadata;

    import ietf-inet-types {
        prefix inet;
    }

    import sonic-types {
        prefix stypes;
    }

    description "DEVICE_NEIGHBOR_METADATA configuration";

    revision 2022-08-25 {
        description "First Revision";
    }

    container sonic-device_neighbor_metadata {

        container DEVICE_NEIGHBOR_METADATA {

            description "Metadata about neighbor devices including HWSKU, type, and management addresses";

            list DEVICE_NEIGHBOR_METADATA_LIST {

                key "name";

                leaf name {
                    description "Host name string, max length 255";
                    type string {
                        length 1..255;
                    }
                }

                leaf cluster {
                    description "The switch is a member of this cluster";
                    type string;
                }

                leaf hwsku {
                    description "Hardware SKU of the neighbor device";
                    type stypes:hwsku;
                }

                leaf lo_addr {
                    description "Device loopback ipv4 address, type of ietf-inet
                                 ipv4-prefix or ipv4-address";
                    type union {
                        type inet:ipv4-prefix;
                        type inet:ipv4-address;
                    }
                }

                leaf lo_addr_v6 {
                    description "Device loopback ipv6 address, type of ietf-inet
                                 ipv6-prefix or ipv6-address";
                    type union {
                        type inet:ipv6-prefix;
                        type inet:ipv6-address;
                    }
                }

                leaf mgmt_addr {
                    description "Device management ipv4 address, type of ietf-inet
                                 ipv4-prefix or ipv4-address";
                    type union {
                        type inet:ipv4-prefix;
                        type inet:ipv4-address;
                    }
                }

                leaf mgmt_addr_v6 {
                    description "Device management ipv6 address, type of ietf-inet
                                 ipv6-prefix or ipv6-address";
                    type union {
                        type inet:ipv6-prefix;
                        type inet:ipv6-address;
                    }
                }

                leaf type {
                    description "Network element type";
                    type string;
                }

                leaf deployment_id {
                    description "Deployment identifier for the neighbor device";
                    type uint32;
                }

                leaf slice_type {
                    description "Metadata tag for the device.";
                    type string;
                }

                leaf resource_type {
                    description "Resource type of the neighbor device (e.g., Storage, Compute).";
                    type string;
                }

            }
            /* end of list DEVICE_NEIGHBOR_METADATA_LIST */
        }
        /* end of container DEVICE_NEIGHBOR_METADATA */
    }
    /* end of container sonic-device_neighbor_metadata */
}
/* end of module sonic-device_neighbor_metadata */
