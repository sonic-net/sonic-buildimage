module sonic-pfc-priority-queue-map {

    yang-version 1.1;

    namespace "http://github.com/sonic-net/sonic-pfc-priority-queue-map";

    prefix ppqm;

    organization
        "SONiC";

    contact
        "SONiC";

    description
        "PFC_PRIORITY_TO_QUEUE_MAP yang Module for SONiC OS";

    revision 2021-04-15 {
        description
            "Initial revision.";
    }

    container sonic-pfc-priority-queue-map {

        container MAP_PFC_PRIORITY_TO_QUEUE {

            description "Maps PFC priority values to egress queues.";

            list MAP_PFC_PRIORITY_TO_QUEUE_LIST {

                key "name";

                description "A named PFC priority to egress queue map.";

                leaf name {
                    type string {
                        pattern '[a-zA-Z0-9]{1}([-a-zA-Z0-9_]{0,31})';
                        length 1..32 {
                            error-message "Invalid length for map name.";
                            error-app-tag map-name-invalid-length;
                        }
                    }
                    description "Name of the PFC priority to queue map.";
                }

                list MAP_PFC_PRIORITY_TO_QUEUE {

                    key "pfc_priority";

                    description "Single mapping entry from a PFC priority to an egress queue.";

                    leaf pfc_priority {
                        type string {
                            pattern "[0-7]?" {
                               error-message "Invalid pfc priority";
                               error-app-tag pfc-priority-invalid;
                            }
                        }
                        description "PFC priority value (0-7).";
                    }

                    leaf qindex {
                        type string {
                            pattern "[0-7]?" {
                               error-message "Invalid queue index";
                               error-app-tag queue-index-invalid;
                            }
                        }
                        description "Target egress queue index (0-7).";
                    }
                }
            }
        }
    }
}
