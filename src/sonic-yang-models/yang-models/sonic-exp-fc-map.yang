module sonic-exp-fc-map {

    yang-version 1.1;

    namespace "http://github.com/sonic-net/sonic-exp-fc-map";

    prefix dtm;

    organization
        "SONiC";

    contact
        "SONiC";

    description
        "EXP_TO_FC_MAP configuration";

    revision 2021-10-29 {
        description
            "Initial revision.";
    }

    container sonic-exp-fc-map {

        container EXP_TO_FC_MAP {

            description "Maps MPLS EXP bits to forwarding class for Class-Based Forwarding.";

            list EXP_TO_FC_MAP_LIST {

                key "name";

                description "A named MPLS EXP to forwarding class map.";

                leaf name {
                    type string {
                        pattern '[a-zA-Z0-9]{1}([-a-zA-Z0-9_]{0,31})';
                        length 1..32 {
                            error-message "Invalid length for map name.";
                            error-app-tag map-name-invalid-length;
                        }
                    }
                    description "Name of the EXP to FC map.";
                }

                list EXP_TO_FC_MAP {

                    key "exp";

                    description "Single mapping entry from an MPLS EXP value to a forwarding class.";

                    leaf exp {
                        type string {
                            pattern "[0-7]?" {
                                error-message "Invalid EXP";
                                error-app-tag exp-invalid;
                            }
                        }
                        description "MPLS EXP bit value (0-7).";
                    }

                    leaf fc {
                        type string {
                            pattern "[0-7]?" {
                                error-message "Invalid Forwarding Class";
                                error-app-tag fc-invalid;
                            }
                        }
                        description "Target forwarding class (0-7) for Class-Based Forwarding.";
                    }
                }
            }
        }
    }
}
