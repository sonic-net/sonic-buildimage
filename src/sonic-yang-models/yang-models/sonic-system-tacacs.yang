module sonic-system-tacacs {
    namespace "http://github.com/sonic-net/sonic-system-tacacs";
    prefix ssys;
    yang-version 1.1;

    import ietf-inet-types {
        prefix inet;
    }

    import sonic-types {
        prefix stypes;
    }

    import sonic-port {
        prefix port;
    }

    import sonic-portchannel {
        prefix lag;
    }

    /*
    import sonic-vlan {
        prefix vlan;
    }
    */

    import sonic-loopback-interface {
        prefix loopback;
    }

    import sonic-mgmt_port {
        prefix mgmt-port;
    }

    description "Terminal Access Controller Access-Control System Plus (TACACS+) configuration";

    revision 2021-04-15 {
        description "Initial revision.";
    }

    typedef auth_type_enumeration {
        type enumeration {
            enum pap;
            enum chap;
            enum mschap;
            enum login;
        }
    }

    typedef key_encrypt_type {
        type boolean;
        default false;
        description "Indicates if the passkey is encrypted.";
    }

    container sonic-system-tacacs {

        container TACPLUS_SERVER {
            description "Per-server TACACS+ configuration entries.";
            list TACPLUS_SERVER_LIST {
                description "A TACACS+ server entry identified by hostname or IP address.";
                max-elements 8;
                key "ipaddress";

                leaf ipaddress {
                    type inet:host;
                    description
                        "TACACS+ server's Domain name or IP address (IPv4 or IPv6)";
                }

                leaf priority {
                    default 1;
                    type uint8 {
                        range "1..64" {
                            error-message "TACACS server priority must be 1..64";
                        }
                    }
                    description "Server selection priority; higher values are tried first.";
                }

                leaf tcp_port {
                    type inet:port-number;
                    default 49;
                    description "TCP port used to communicate with this TACACS+ server.";
                }

                leaf timeout {
                    default 5;
                    type uint16 {
                        range "1..60" {
                            error-message "TACACS server timeout must be 1..60";
                        }
                    }
                    description "Per-server response timeout in seconds.";
                }

                leaf auth_type {
                    type auth_type_enumeration;
                    default pap;
                    description "Per-server authentication protocol (pap, chap, mschap, or login).";
                }

                leaf key_encrypt {
                    type key_encrypt_type;
                    description "Indicates whether the per-server passkey is stored encrypted.";
                }

                leaf passkey {
                    type string {
                        length "1..256";
                        pattern "[^ #,]*" {
                            error-message 'TACACS shared secret (Valid chars are ASCII printable except SPACE, "#", and ",")';
                        }
                    }
                    description "Per-server shared secret overriding the global passkey.";
                }

                leaf vrf {
                    type string {
                        pattern "mgmt|default" {
                            error-message "Error: Invalid VRF name";
                        }
                    }
                    description "VRF used to reach this TACACS+ server (mgmt or default).";
                }
            }
        }

        container TACPLUS {
            description "Global TACACS+ client configuration.";

            container global {
                description "Global TACACS+ authentication settings applied to all servers.";

                leaf auth_type {
                    type auth_type_enumeration;
                    default pap;
                    description "Default authentication protocol for TACACS+ communication.";
                }

                leaf timeout {
                    type uint16 {
                        range "1..60" {
                            error-message "TACACS timeout must be 1..60";
                        }
                    }
                    default 5;
                    description "Default timeout in seconds for TACACS+ server responses.";
                }

                leaf key_encrypt {
                    type key_encrypt_type;
                    description "Indicates whether the global passkey is stored encrypted.";
                }

                leaf passkey {
                    type string {
                        length "1..256";
                        pattern "[^ #,]*" {
                            error-message 'TACACS shared secret (Valid chars are ASCII printable except SPACE, "#", and ",")';
                        }
                    }
                    description "Default shared secret for authenticating TACACS+ server communication.";
                }

                leaf src_intf {
                    type union {
                        type leafref {
                            path "/port:sonic-port/port:PORT/port:PORT_LIST/port:name";
                        }
                        type leafref {
                            path "/lag:sonic-portchannel/lag:PORTCHANNEL/lag:PORTCHANNEL_LIST/lag:name";
                        }
                        /*
                        type leafref {
                            path "/vlan:sonic-vlan/vlan:VLAN/vlan:VLAN_LIST/vlan:name";
                        }
                        */
                        type string {
                            pattern 'Vlan([0-9]{1,3}|[1-3][0-9]{3}|[4][0][0-8][0-9]|[4][0][9][0-4])';
                        }
                        type leafref {
                            path "/loopback:sonic-loopback-interface/loopback:LOOPBACK_INTERFACE/loopback:LOOPBACK_INTERFACE_LIST/loopback:name";
                        }
                        type leafref {
                            path "/mgmt-port:sonic-mgmt_port/mgmt-port:MGMT_PORT/mgmt-port:MGMT_PORT_LIST/mgmt-port:name";
                        }
                    }
                    description "Source interface whose IP address is used for outgoing TACACS+ packets.";
                }

                leaf traceid_authorization {
                    type stypes:boolean_type;
                    default false;
                    description "Enable adding validated SSH_CLIENT_TRACEID values as the TACACS+ traceid command authorization attribute.";
                }
            }
        }
    }
}
