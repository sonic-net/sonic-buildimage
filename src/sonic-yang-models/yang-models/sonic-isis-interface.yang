module sonic-isis-interface {
    yang-version 1.1;
    namespace "http://github.com/sonic-net/sonic-isis-interface";
    prefix isis-if;

    import sonic-isis-global {
        prefix isisg;
    }
    import sonic-port {
        prefix port;
    }
    import sonic-portchannel {
        prefix lag;
    }
    import sonic-vlan {
        prefix vlan;
    }
    import sonic-loopback-interface {
        prefix lo;
    }
    import sonic-vlan-sub-interface {
        prefix sub;
    }

    organization
        "SONiC";
    description
        "Explicit IS-IS circuit bindings and per-level parameters.";

    revision 2026-11-10 {
        description
            "Separate instance binding, address families, network type and levels.";
    }

    container sonic-isis-interface {
        container ISIS_INTERFACE {
            list ISIS_INTERFACE_LIST {
                key "ifname";
                leaf ifname {
                    type union {
                        type leafref {
                            path "/port:sonic-port/port:PORT/port:PORT_LIST/port:name";
                        }
                        type leafref {
                            path "/lag:sonic-portchannel/lag:PORTCHANNEL/lag:PORTCHANNEL_LIST/lag:name";
                        }
                        type leafref {
                            path "/vlan:sonic-vlan/vlan:VLAN_INTERFACE/vlan:VLAN_INTERFACE_LIST/vlan:name";
                        }
                        type leafref {
                            path "/lo:sonic-loopback-interface/lo:LOOPBACK_INTERFACE/lo:LOOPBACK_INTERFACE_LIST/lo:name";
                        }
                        type leafref {
                            path "/sub:sonic-vlan-sub-interface/sub:VLAN_SUB_INTERFACE/sub:VLAN_SUB_INTERFACE_LIST/sub:name";
                        }
                    }
                    description
                        "The physical or logical interface name enabled for IS-IS.";
                }
                leaf vrf {
                    type leafref {
                        path "/isisg:sonic-isis-global/isisg:ISIS_INSTANCE/isisg:ISIS_INSTANCE_LIST/isisg:vrf";
                    }
                    mandatory true;
                }
                leaf instance {
                    type leafref {
                        path "/isisg:sonic-isis-global/isisg:ISIS_INSTANCE/isisg:ISIS_INSTANCE_LIST[isisg:vrf=current()/../vrf]"
                              + "/isisg:instance";
                    }
                    mandatory true;
                }
                leaf enabled {
                    type boolean;
                    default "false";
                }
                leaf ipv4_enabled {
                    type boolean;
                    default "false";
                }
                leaf ipv6_enabled {
                    type boolean;
                    default "false";
                }
                leaf passive {
                    type boolean;
                    default "false";
                }
                leaf level_type {
                    type enumeration {
                        enum level-1;
                        enum level-2-only;
                        enum level-1-2;
                    }
                    default "level-1-2";
                }
                leaf network_type {
                    type enumeration {
                        enum broadcast;
                        enum point-to-point;
                    }
                    default "broadcast";
                }
            }
        }
        container ISIS_INTERFACE_LEVEL {
            list ISIS_INTERFACE_LEVEL_LIST {
                key "ifname level";
                leaf ifname {
                    type leafref {
                        path "../../../ISIS_INTERFACE/ISIS_INTERFACE_LIST/ifname";
                    }
                    mandatory true;
                }
                leaf level {
                    type enumeration {
                        enum level-1;
                        enum level-2;
                    }
                }
                leaf metric {
                    type uint32 {
                        range "0..16777215";
                    }
                    default "10";
                }
                leaf hello_interval {
                    type uint32 {
                        range "1..600";
                    }
                    units "seconds";
                    default "3";
                }
                leaf hello_multiplier {
                    type uint32 {
                        range "2..100";
                    }
                    default "10";
                }
            }
        }
    }
}
