module sonic-vlan {

	yang-version 1.1;

	namespace "http://github.com/sonic-net/sonic-vlan";
	prefix vlan;

	import ietf-inet-types {
		prefix inet;
	}

	import ietf-yang-types {
		prefix yang;
	}

	import sonic-types {
		prefix stypes;
	}

	import sonic-port {
		prefix port;
		revision-date 2019-07-01;
	}

	import sonic-portchannel {
		prefix lag;
	}

	import sonic-vrf {
		prefix vrf;
	}

	import sonic-mirror-session {
		prefix sms;
	}
	import sonic-interface {
		prefix intf;
	}
	
	import sonic-vnet {
		prefix svnet;
	}

	import sonic-static-anycast-gateway {
		prefix sag;
	}

	description "VLAN yang Module for SONiC OS";

	revision 2026-10-30 {
		description "Count priority-tagged VLAN members in the one-untagged-VLAN-per-port check.";
	}

	revision 2025-04-22 {
		description "Add SAG support";
	}

	revision 2025-03-06 {
		description "Add leaf vnet_name";
	}

	revision 2024-03-07 {
		description "Add Constraints that are implemented in CLI";
	}
	revision 2021-04-28 {
		description "Modify Vlan name constraint to allow only legal Vlan names";
	}

	revision 2021-04-22 {
		description "Modify Vlan Member to include PortChannel along with Port";
	}

	revision 2021-03-30 {
		description "Modify the type of vrf name";
	}

	revision 2019-07-01 {
		description "First Revision";
	}

	container sonic-vlan {

		container VLAN_INTERFACE {

			description "Layer 3 IP interface configuration for VLANs";

			list VLAN_INTERFACE_LIST {

				description "VLAN interface with optional VRF binding and interface attributes";

				key "name";

				leaf name {
					description "VLAN interface name (e.g., Vlan100)";
					type leafref {
						path "/vlan:sonic-vlan/vlan:VLAN/vlan:VLAN_LIST/vlan:name";
					}
				}

				leaf vrf_name {
					description "VRF instance this VLAN interface belongs to";
					type leafref{
						path "/vrf:sonic-vrf/vrf:VRF/vrf:VRF_LIST/vrf:name";
					}
				}
				
				leaf vnet_name {
					description "Reference to the name of a VNET in sonic-vnet model";
					type leafref {
						path "/svnet:sonic-vnet/svnet:VNET/svnet:VNET_LIST/svnet:name";
					}   
				}

				leaf nat_zone {
					description "NAT Zone for the vlan interface";
					type uint8 {
						range "0..3" {
							error-message "Invalid nat zone for the vlan interface.";
							error-app-tag nat-zone-invalid;
						}
					}
					default "0";
				}
				leaf mpls {
					description "Enable/disable MPLS routing for the vlan interface";
					type enumeration {
						enum enable;
						enum disable;
					}
				}

				leaf grat_arp {
					description "Enable or disable gratuitous ARP on the VLAN interface";
					type string {
						pattern "enabled|disabled";
					}
				}

				leaf proxy_arp {
					description "Enable or disable proxy ARP on the VLAN interface";
					type string {
						pattern "enabled|disabled";
					}
				}

				leaf ipv6_use_link_local_only {
					description "Enable/Disable IPv6 link local address on vlan interface";
					type stypes:mode-status;
					default disable;
				}

				leaf static_anycast_gateway {
					description
						"Enable/disable static anycast gateway for the vlan interface.
						 Requires SAG GLOBAL gateway_mac to be configured when enabled.";
					type stypes:boolean_type;
					default "false";
					/* SAG GLOBAL gateway_mac must exist before enabling static anycast gateway on a VLAN interface. */
					must "current() = 'false' or /sag:sonic-static-anycast-gateway/sag:SAG/sag:SAG_LIST[sag:name='GLOBAL']/sag:gateway_mac" {
						error-message "static_anycast_gateway requires SAG GLOBAL gateway_mac to be configured";
						error-app-tag static-anycast-gateway-requires-global-mac;
					}
				}

				leaf mac_addr {
					description "Assign administrator-provided MAC address to Interface";
					type yang:mac-address;
				}

				leaf loopback_action {
					description "Packet action when a packet ingress and gets routed on the same IP interface";
					type stypes:loopback_action;
				}
			}
			/* end of VLAN_INTERFACE_LIST */

			list VLAN_INTERFACE_IPPREFIX_LIST {

				key "name ip-prefix";

				leaf name {
					description "VLAN interface name (e.g., Vlan100)";
					/* This node must be present in VLAN_INTERFACE_LIST */
					must "(current() = ../../VLAN_INTERFACE_LIST[name=current()]/name)"
					{
						error-message "Must condition not satisfied, Try adding Vlan<vlanid>: {}, Example: 'Vlan100': {}";
					}

					type leafref {
						path "/vlan:sonic-vlan/vlan:VLAN/vlan:VLAN_LIST/vlan:name";
					}
				}

				leaf ip-prefix {
					description "IP address and prefix length assigned to the VLAN interface";
					type stypes:sonic-ip-address-with-prefix;
				}

				leaf scope {
					description "Address scope, either global or link-local";
					type enumeration {
						enum global;
						enum local;
					}
				}

				leaf family {
					description "Address family (IPv4 or IPv6)";

					/* family leaf needed for backward compatibility
						Both ip4 and ip6 address are string in IETF RFC 6021,
						so must statement can check based on : or ., family
						should be IPv4 or IPv6 according.
					 */

					must "(contains(../ip-prefix, ':') and current()='IPv6') or
						(contains(../ip-prefix, '.') and current()='IPv4')";
					type stypes:ip-family;
				}

				leaf secondary	{
					description "Optional field to specify if the prefix is secondary subnet";
					type boolean;
				}
			}
			/* end of VLAN_INTERFACE_IPPREFIX_LIST */
		}
		/* end of VLAN_INTERFACE container */

		container VLAN {

			description "IEEE 802.1Q VLAN definitions";

			list VLAN_LIST {

				key "name";

				leaf name {
					description "VLAN name in the form VlanNNN (e.g., Vlan100)";
					type string {
						pattern 'Vlan(409[0-5]|40[0-8][0-9]|[1-3][0-9]{3}|[1-9][0-9]{2}|[1-9][0-9]|[2-9])';
					}
				}
				leaf vlanid {
					description "IEEE 802.1Q VLAN identifier (2-4094)";
					type uint16 {
						range 2..4094;
					}
					must "substring-after(../name, 'Vlan') = current()"{
						error-message "The vlanid must correspond to the VLAN name";
					}
				}

				leaf alias {
					description "User-defined alias for the VLAN";
					type string;
				}

				leaf description {
					type string {
						length 1..255;
					}
				}

				leaf-list dhcp_servers {
					description "Configure the dhcp v4 servers";
					type inet:ip-address;
					ordered-by user;
				}

				leaf-list dhcpv6_servers {
					description "Configure the dhcp v6 servers";
					type inet:ipv6-address;
					ordered-by user;
				}

				leaf mtu {
					type uint16 {
						range 1..9216;
					}
				}

				leaf admin_status {
					type stypes:admin_status;
				}

				leaf mac {
					type yang:mac-address;
				}
			}
			/* end of VLAN_LIST */
		}
		/* end of container VLAN */

		container VLAN_MEMBER {

			description "VLAN port membership and tagging configuration";

			list VLAN_MEMBER_LIST {

				key "name port";

				leaf name {
					description "VLAN name this member belongs to";
					type leafref {
						path "/vlan:sonic-vlan/vlan:VLAN/vlan:VLAN_LIST/vlan:name";
					}
				}
				leaf port {
					description "Physical port or port channel assigned to this VLAN";
					/* key elements are mandatory by default */
					type union {
						type leafref {
							path "/port:sonic-port/port:PORT/port:PORT_LIST/port:name";
						}
						type leafref {
							path "/lag:sonic-portchannel/lag:PORTCHANNEL/lag:PORTCHANNEL_LIST/lag:name";
						}
					}
					must "not(/sms:sonic-mirror-session/sms:MIRROR_SESSION/sms:MIRROR_SESSION_LIST[sms:dst_port=current()])"
					{
						error-message "Port is used as a destination port in a mirror session.";
					}
					must "not(/lag:sonic-portchannel/lag:PORTCHANNEL_MEMBER/lag:PORTCHANNEL_MEMBER_LIST[lag:port=current()]/lag:name)" {
						error-message "Port is a member of a port channel.";
					}
					must "not(/intf:sonic-interface/intf:INTERFACE/intf:INTERFACE_LIST[intf:name=current()])" {
						error-message "Port is a router interface.";
					}
					/* Untagged and priority-tagged members both set the port VLAN ID, and a port has only one. */
					must "count(../../vlan:VLAN_MEMBER_LIST[vlan:port=current() and
						(vlan:tagging_mode='untagged' or vlan:tagging_mode='priority_tagged')]) <= 1" {
						error-message "Port can be untagged or priority-tagged in at most one VLAN.";
						error-app-tag vlan-member-multiple-pvid;
					}
				}
				leaf tagging_mode {
					description "Whether frames on this port are IEEE 802.1Q tagged, untagged, or priority-tagged";
					mandatory true;
					type stypes:vlan_tagging_mode;
				}
			}
			/* end of list VLAN_MEMBER_LIST */
		}
		/* end of container VLAN_MEMBER */
	}
	/* end of container sonic-vlan */
}
/* end of module sonic-vlan */
