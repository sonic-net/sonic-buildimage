//filename:  sonic-serial-console.yang
module sonic-serial-console {
    yang-version 1.1;
    namespace "http://github.com/Azure/sonic-serial-console";
    prefix cli-sessions;
    import sonic-types {
        prefix stypes;
    }
    description "Serial console session policy configuration";
    revision 2023-06-07 {
        description "First Revision";
    }
    container sonic-serial-console {
        container SERIAL_CONSOLE {
            description "Serial console session configuration.";
            container POLICIES {
                description "Serial console session timeout and security policies.";
                leaf inactivity_timeout {
                    description "Serial console inactivity timeout in minutes; 0 disables the timeout.";
                    type int32 {
                        range "0..35000";
                    }
                    default 15;
                }

                leaf sysrq_capabilities {
                    type stypes:admin_mode;
                    description "Enable or disable Linux SysRq key capabilities on the serial console.";
                    default disabled;
                }
        }
        /* end of container POLICIES */
        }
        /* end of container SERIAL_CONSOLE */
    }
    /* end of top level container */
}
/* end of module sonic-serial-console */
