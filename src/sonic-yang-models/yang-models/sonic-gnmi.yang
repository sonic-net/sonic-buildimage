module sonic-gnmi {

    yang-version 1.1;

    namespace "http://github.com/sonic-net/sonic-gnmi";
    prefix gnmi;

    import ietf-inet-types {
        prefix inet;
    }
    import sonic-mgmt_vrf {
        prefix mvrf;
    }

    organization
        "SONiC";

    contact
        "SONiC";

    description "GNMI configuration";

    revision 2025-09-01 {
        description "Add VRF support for GNMI service";
    }
    revision 2023-02-10 {
        description "First Revision";
    }

    typedef vrf-device {
        description "Represents GNMI VRF device";
        type enumeration {
            enum default;
            enum mgmt;
        }
    }

    container sonic-gnmi {

        container GNMI {

            description "gRPC Network Management Interface server configuration.";

            container certs {
                description "TLS certificate paths for the gNMI server.";

                leaf ca_crt {
                    type string {
                        pattern '(/[a-zA-Z0-9_-]+)*/([a-zA-Z0-9_-]+).cer';
                    }
                    description "Local path for ca_crt.";
                }

                leaf server_crt {
                    type string {
                        pattern '(/[a-zA-Z0-9_-]+)*/([a-zA-Z0-9_-]+).cer';
                    }
                    description "Local path for server_crt.";
                }

                leaf server_key {
                    type string {
                        pattern '(/[a-zA-Z0-9_-]+)*/([a-zA-Z0-9_-]+).key';
                    }
                    description "Local path for server_key.";
                }

            }

            container gnmi {
                description "gNMI server operational settings.";

                leaf client_auth {
                    type boolean;
                    description "Flag for requiring client auth.";
                }

                leaf log_level {
                    type uint8 {
                        range 0..100;
                    }
                    description "Log level for gnmi.";
                }

                leaf port {
                    type inet:port-number;
                    description "Port gnmi runs on.";
                }

                leaf save_on_set {
                    type boolean;
                    description "Flag for enabling save on set.";
                }

                leaf enable_crl {
                    type boolean;
                    description "Flag for enable certificate revocation list.";
                }

                leaf crl_expire_duration {
                    type uint32;
                    description "Certificate revocation list cache expire duration.";
                }

                leaf user_auth {
                    type string {
                        pattern 'password|jwt|cert|none';
                    }
                    default "cert";
                    description "GNMI service user authorization type.";
                }

                leaf vrf {
                    type vrf-device;
                    must "(current() != 'mgmt')
                    or (/mvrf:sonic-mgmt_vrf/mvrf:MGMT_VRF_CONFIG/mvrf:vrf_global/mvrf:mgmtVrfEnabled = 'true')";
                    description "VRF for GNMI. Only 'default' and 'mgmt' are supported.";
                }
            }
        }

        container GNMI_CLIENT_CERT {
            description "GNMI client cert list";

            list GNMI_CLIENT_CERT_LIST {
                key "cert_cname";

                leaf cert_cname {
                    type string;
                    description
                        "client cert common name";
                }

                leaf-list role {
                    type string;
                    min-elements 1;
                    description
                        "role of client cert common name";
                }
            }
        }
    }
}
