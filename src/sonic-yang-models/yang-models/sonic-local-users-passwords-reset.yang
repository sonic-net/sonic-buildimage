module sonic-local-users-passwords-reset {
    yang-version 1.1;
    namespace "http://github.com/sonic-net/local-users-passwords-reset";
    prefix local_users_passwords_reset;

    import sonic-types {
        prefix stypes;
    }

    description "LOCAL_USERS_PASSWORDS_RESET YANG Module for SONiC-based OS";
    revision 2024-01-04 {
        description "First Revision";
    }

    container sonic-local-users-passwords-reset {
        container LOCAL_USERS_PASSWORDS_RESET {
            description "LOCAL_USERS_PASSWORDS_RESET part of config_db.json";
            container global {
                leaf state {
                    type stypes:admin_mode;
                    description "Local users' passwords reset feature state";
                    default disabled;
                }
            } /* end of container global */
        } /* end of container LOCAL_USERS_PASSWORDS_RESET */
    } /* end of top level container */
}
