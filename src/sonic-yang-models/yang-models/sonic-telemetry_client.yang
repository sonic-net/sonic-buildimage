module sonic-telemetry_client {

    yang-version 1.1;

    namespace "http://github.com/sonic-net/sonic-telemetry_client";
    prefix telemetry_client;

    import ietf-inet-types {
        prefix inet;
    }

    organization
        "SONiC";

    contact
        "SONiC";

    description
        "TELEMETRY_CLIENT configuration";

    revision 2023-01-12 {
        description
            "First revision";
    }

    typedef report-type {
        description "Subscription reporting mode for dial-out telemetry.";
        type enumeration {
            enum periodic;
            enum stream;
            enum once;
        }
    }
    typedef path_target {
        description "Database target for telemetry subscriptions.";
        type enumeration {
            enum APPL_DB;
            enum CONFIG_DB;
            enum COUNTERS_DB;
            enum STATE_DB;
            enum OTHERS;
        }
    }

    typedef encoding {
        description "Wire encoding format for telemetry data.";
        type enumeration {
            enum JSON_IETF;
            enum ASCII;
            enum BYTES;
            enum PROTO;
        }
    }

    typedef ipv4-port {
        description "One or more IPv4 address and port pairs in host:port format, comma-separated.";
        type string {
            pattern
                '((([0-9]|[1-9][0-9]|1[0-9][0-9]|2[0-4][0-9]|25[0-5])\.){3}'
            +  '([0-9]|[1-9][0-9]|1[0-9][0-9]|2[0-4][0-9]|25[0-5]):'
            +  '([0-9]|[1-9]\d{1,3}|[1-5]\d{1,4}|6[0-4]\d{1,3}|65[0-4]\d{1,2}|655[0-2][0-9]|6553[0-5]),?)+';
        }
      }

    container sonic-telemetry_client{

        container TELEMETRY_CLIENT {
            description "Telemetry dial-out client configuration.";
            container Global {
                description "Global settings for the telemetry dial-out client.";
                leaf retry_interval {
                    type uint64;
                    description "retry_interval unit s";
                }

                leaf src_ip {
                    type inet:ip-address;
                    description "Source IP address for dial-out connections.";
                }

                leaf encoding {
                    type encoding;
                    description "Data encoding format for telemetry messages.";
                }

                leaf unidirectional {
                    type boolean;
                    default true;
                    description "Whether the dial-out connection is unidirectional.";
                }
            }

            list TELEMETRY_CLIENT_LIST {
                description "Subscription and destination group entries for dial-out telemetry.";
                ordered-by user;
                key "prefix name";

                leaf prefix {
                    type string {
                        pattern 'Subscription|DestinationGroup';
                    }
                    description "Entry type: Subscription or DestinationGroup.";
                }

                leaf name {
                    type string;
                    description "Name of this subscription or destination group.";
                }

                leaf dst_addr {
                    type ipv4-port;
                    description "Collector address and port in host:port format.";
                }

                leaf dst_group {
                    must "(contains(../../TELEMETRY_CLIENT_LIST/name, current()))";
                    type string;
                    description "Destination group name this subscription sends data to.";
                }

                leaf path_target {
                    type path_target;
                    description "Target database to subscribe to.";
                }

                leaf paths {
                    type string;
                    description "Comma-separated data paths to subscribe to within the target database.";
                }

                leaf report_interval {
                    type uint64;
                    description "report_interval unit ms";
                    default 5000;
                }

                leaf report_type {
                    type report-type;
                    description "Reporting mode for this subscription.";
                }
            }
        }
    }
}
