module sonic-kubernetes_master {

    yang-version 1.1;

    namespace "http://github.com/sonic-net/sonic-kubernetes_master";

    prefix kubernetes_master;

    import ietf-inet-types {
        prefix inet;
    }

    import sonic-types {
        prefix stypes;
    }

    description "KUBERNETES_MASTER configuration";

    revision 2022-10-09 {
        description "First Revision";
    }

    container sonic-kubernetes_master {

        container KUBERNETES_MASTER {

            description "Kubernetes master server endpoint and connection settings";

            container SERVER {
                description "Kubernetes API server connection parameters";

                leaf ip {
                    description "Kubernetes api server endpoint(an IP address or a DNS
                                domain name.)";
                    type inet:host;
                }

                leaf port {
                    description "Kubernetes api server port";
                    type inet:port-number;
                    default 6443;
                }

                leaf disable {
                    description "Whether to disable Kubernetes integration";
                    type stypes:boolean_type;
                    default "false";
                }

                leaf insecure {
                    description "Whether to disable HTTPS server certificate verification
                                when downloading the Kubernetes CA certificate";
                    type stypes:boolean_type;
                    default "false";
                }

            }
            /* end of container SERVER */
        }
        /* end of container KUBERNETES_MASTER */
    }
    /* end of top level container */
}
/* end of module sonic-kubernetes_master */
