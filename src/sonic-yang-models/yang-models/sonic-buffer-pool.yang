module sonic-buffer-pool {
    namespace "http://github.com/sonic-net/sonic-buffer-pool";
    prefix bpl;

    import sonic-device_metadata {
        prefix device_metadata;
    }

    organization
        "SONiC";

    contact
        "SONiC";

    description
        "Shared and dedicated memory pool configuration for packet buffering.";

    revision 2021-07-01 {
        description
            "Initial revision.";
    }

    container sonic-buffer-pool {

        container BUFFER_POOL {

            description "Configures ingress and egress buffer pools with size, threshold, and sharing mode.";

            list BUFFER_POOL_LIST {

                description "A named buffer pool entry.";
                key "name";

                leaf name {
                    type string;
                    description "Buffer Pool name";
                }

                leaf type {
                    mandatory true;
                    type enumeration {
                        enum ingress;
                        enum egress;
                        enum both;
                    }
                    description "Buffer Pool Type";
                }

                leaf mode {
                    mandatory true;
                    type enumeration {
                        enum static;
                        enum dynamic;
                    }
                    description "Buffer Pool Mode";
                }

                leaf size {
                    type uint64;
                    description "Buffer Pool Size (in Bytes)";
                }

                leaf xoff {
                    default 0;
                    type uint64;
                    description "Buffer Pool Xoff Threshold (in Bytes)";
                }

                leaf percentage {
                    type uint8;
                    description "
                        Buffer Pool percentage.
                        The buffer pool size will be available_buffer * percentage / 100 if percentage is provided.
                        It is valid in dynamic buffer model only.";
                    must "(not(current()/../size))" {
                        error-message "Percentage should not be configured along with size";
                    }
                    must "/device_metadata:sonic-device_metadata/device_metadata:DEVICE_METADATA/device_metadata:localhost/device_metadata:buffer_model = 'dynamic'" {
                        error-message "Percentage must be configured in dynamic buffer model";
                    }
                }
            }
        }
    }
}
