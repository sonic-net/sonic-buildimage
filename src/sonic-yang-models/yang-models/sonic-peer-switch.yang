module sonic-peer-switch {
    yang-version 1.1;
    namespace "http://github.com/sonic-net/sonic-peer-switch";
    prefix peer_switch;

    import ietf-inet-types {
        prefix inet;
    }

    import sonic-types {
        prefix stypes;
    }

    organization
        "SONiC";

    contact
        "SONiC";

    description
        "DualToR peer switch data";

    revision 2022-08-23 {
        description
            "Initial revision";
    }

    container sonic-peer-switch {
        container PEER_SWITCH {
            list PEER_SWITCH_LIST {
                max-elements 1;

                key "peer_switch";

                leaf peer_switch {
                    type stypes:hostname;

                    description "DualToR peer host name.";
                }

                leaf address_ipv4 {
                    type inet:ipv4-address;

                    description "DualToR peer's IPv4 address.";
                }
            }
        }
    }
}
