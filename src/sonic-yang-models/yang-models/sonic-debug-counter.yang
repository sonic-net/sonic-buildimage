module sonic-debug-counter {
    namespace "http://github.com/sonic-net/sonic-debug-counter";
    prefix dbgcnt;
    yang-version 1.1;

    import sonic-types {
		prefix stypes;
    }

    organization
        "SONiC";

    contact
        "SONiC";

    description
        "Debug Counter configuration";

    revision 2024-03-07 {
        description
            "Initial revision";
    }

    container sonic-debug-counter{
        container DEBUG_COUNTER {
            description "Configurable packet drop counters for debugging.";
            list DEBUG_COUNTER_LIST {
                key "name";

                leaf name {
                    type string;
                    description "Unique name for this debug counter.";
                }

                leaf alias {
                    type string;
                    description "Alias of the counter";
                }

                leaf desc {
                    type string;
                    description "Description of counter (can include counter type, intended use, etc.)";
                }

                leaf group {
                    type string;
                    description "Group name to organize counters";
                }

                leaf drop_monitor_status {
                    type stypes:admin_mode;
                    default "disabled";
                    description "Indicates whether the feature is enabled or disabled.";
                }

                leaf window {
                    type uint64;
                    default 900;
                    units seconds;
                    description "The length of the time window in seconds";
                }

                leaf incident_count_threshold {
                    type uint64;
                    default 3;
                    description "The number of incidents that have to occur per window for it to be registered as a syslog";
                }

                leaf drop_count_threshold {
                    type uint64;
                    default 100;
                    description "The number of packet drops required for being classified as an incident";
                }

                leaf type {
                    type stypes:debug_counter_type;
                    mandatory true;
                    description "Counter type indicating scope (switch or port) and direction (ingress or egress)";
                }
            }
        }

        container DEBUG_COUNTER_DROP_REASON {
            description "Drop reasons assigned to each debug counter.";
            list DEBUG_COUNTER_DROP_REASON_LIST {
                key "name reason";

                leaf name {
                    /* Counter must first be created in DEBUG_COUNTER_TABLE before we can add reasons to it */
                    must "(current() = ../../../DEBUG_COUNTER/DEBUG_COUNTER_LIST[name=current()]/name)" {
                        error-message "The counter does not exist in the DEBUG_COUNTER table";
                    }
                    type string;
                    description "Name of the debug counter this reason belongs to.";
                }

                leaf reason {
                    type stypes:counter_drop_reason;
                    description "Drop reason which will cause the counter to increment";
                }
            }
        }

        container DEBUG_DROP_MONITOR {
            description "Global debug drop monitor settings.";
            container CONFIG {
                description "Global configuration for persistent drop monitoring.";

                leaf status {
                    type stypes:admin_mode;
                    default "disabled";
                    description "Indicates whether the feature is enabled or disabled.";
                }
            }
        }
    }
}
