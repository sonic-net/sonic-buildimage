module sonic-evpn {
    yang-version 1.1;

    namespace "http://github.com/sonic-net/sonic-evpn";
    prefix sevpn;

    import sonic-port {
        prefix port;
    }

    import sonic-portchannel {
        prefix lag;
    }

    organization
        "SONiC";

    contact
        "SONiC";

    description
        "SONIC EVPN";

    revision 2026-05-27 {
        description
            "Initial EVPN multihoming model.";
    }

    typedef esi-type {
        type enumeration {
            enum TYPE_0_OPERATOR_CONFIGURED {
                value 0;
                description "Type 0 ESI - Operator Configured";
            }
            enum TYPE_3_MAC_BASED {
                value 3;
                description "Type 3 ESI - MAC-Based ESI";
            }
        }
    }

    container sonic-evpn {

        container EVPN_ETHERNET_SEGMENT {
            description "CONFIG_DB EVPN_ETHERNET_SEGMENT Table";

            list EVPN_ETHERNET_SEGMENT_LIST {

                key "ifname";

                leaf ifname {
                    type union {
                        type leafref {
                            path "/port:sonic-port/port:PORT/port:PORT_LIST/port:name";
                        }
                        type leafref {
                            path "/lag:sonic-portchannel/lag:PORTCHANNEL/lag:PORTCHANNEL_LIST/lag:name";
                        }
                    }
                }

                leaf esi {
                    mandatory true;
                    type string {
                        /*
                         * Valid ESIs include:
                         * AUTO (Anything but Type 0)
                         * 00:01:02:03:04:05:06:07:08:09 (Only Type 0)
                         */
                        pattern "AUTO|([a-fA-F0-9]{2}:){9}[a-fA-F0-9]{2}" {
                            error-message "Provided ESI is not valid";
                            error-app-tag esi-invalid;
                        }
                    }
                }

                leaf type {
                    mandatory true;
                    type esi-type;
                }

                leaf df_pref {
                    type uint16 {
                        range "1..65535" {
                            error-message "DF Preference value out of range";
                            error-app-tag df-pref-invalid;
                        }
                    }
                    default 32767;
                }

                /*
                 * Type 0 ESIs must be operator configured and must use the
                 * canonical Type 0 format with a leading 00 octet.
                 * 'AUTO' ESI is mandatory for all other ESI types.
                 */
                must "(type = 'TYPE_0_OPERATOR_CONFIGURED' and esi != 'AUTO' and " +
                     "substring(esi, 1, 3) = '00:') or " +
                     "(type != 'TYPE_0_OPERATOR_CONFIGURED' and esi = 'AUTO')" {
                    error-message "Invalid ESI/type combination: Type 0 requires manual '00:' ESI; non-Type 0 requires AUTO ESI";
                    error-app-tag auto-esi-type-invalid;
                }

                /* The all-zero ESI is reserved and must not be configured. */
                must "esi != '00:00:00:00:00:00:00:00:00:00'" {
                    error-message "Reserved all-zero ESI is not allowed";
                    error-app-tag reserved-esi-invalid;
                }
            }
        }
        container EVPN_MH_GLOBAL {
            description "CONFIG_DB EVPN_MH_GLOBAL Table";

            list EVPN_MH_GLOBAL_LIST {
                key "name";
                max-elements 1;

                leaf name {
                    description "EVPN_MH_GLOBAL singleton entry name. Only default is valid.";
                    type string {
                        pattern "default" {
                            error-message "EVPN_MH_GLOBAL entry name must be default";
                            error-app-tag evpn-mh-global-name-invalid;
                        }
                    }
                }

                leaf startup_delay {
                    type uint16 {
                        range "0..3600" {
                            error-message "Startup Delay value out of range";
                            error-app-tag startup-delay-invalid;
                        }
                    }
                    default 300;
                }

                leaf mac_holdtime {
                    type uint32 {
                        range "0..86400" {
                            error-message "MAC Holdtime value out of range";
                            error-app-tag mac-holdtime-invalid;
                        }
                    }
                    default 1080;
                }


                leaf neigh_holdtime {
                    type uint32 {
                        range "0..86400" {
                            error-message "Neighbor Holdtime value out of range";
                            error-app-tag neigh-holdtime-invalid;
                        }
                    }
                    default 1080;
                }
            }
        }
    }
}
