module sonic-pfc-priority-priority-group-map {

    yang-version 1.1;

    namespace "http://github.com/sonic-net/sonic-pfc-priority-priority-group-map";

    prefix pppgm;

    organization
        "SONiC";

    contact
        "SONiC";

    description
        "PFC_PRIORITY_TO_PRIORITY_GROUP_MAP yang Module for SONiC OS";

    revision 2021-04-15 {
        description
            "Initial revision.";
    }

    container sonic-pfc-priority-priority-group-map {

        container PFC_PRIORITY_TO_PRIORITY_GROUP_MAP {

            description "Maps PFC priority values to ingress priority groups for lossless traffic handling.";

            list PFC_PRIORITY_TO_PRIORITY_GROUP_MAP_LIST {

                key "name";

                description "A named PFC priority to priority group map.";

                leaf name {
                    type string {
                        pattern '[a-zA-Z0-9]{1}([-a-zA-Z0-9_]{0,31})';
                        length 1..32 {
                            error-message "Invalid length for map name.";
                            error-app-tag map-name-invalid-length;
                        }
                    }
                    description "Name of the PFC priority to priority group map.";
                }

                list PFC_PRIORITY_TO_PRIORITY_GROUP_MAP {

                    key "pfc_priority";

                    description "Single mapping entry from a PFC priority to a priority group.";

                    leaf pfc_priority {
                        type string {
                            pattern "[0-7]?" {
                               error-message "Invalid pfc priority";
                               error-app-tag pfc-priority-invalid;
                            }
                        }
                        description "PFC priority value (0-7).";
                    }

                    leaf pg {
                        type string {
                            pattern "[0-7]?" {
                                error-message "Invalid Priority Group";
                                error-app-tag pg-invalid;
                            }
                        }
                        description "Target ingress priority group (0-7).";
                    }
                }
            }
        }
    }
}
