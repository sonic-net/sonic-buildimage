module sonic-mgmt_port {

    yang-version 1.1;

    namespace "http://github.com/sonic-net/sonic-mgmt_port";
    prefix mgmtprt;

    import sonic-types {
        prefix stypes;
    }

    description "Out-of-band management port physical properties configuration";

    revision 2021-04-07 {
        description "First Revision";
    }

    container sonic-mgmt_port {

        container MGMT_PORT {

            description "Management port physical properties configuration table";

            list MGMT_PORT_LIST {

                description "Physical properties for an out-of-band management port";

                key "name";

                leaf name {
                    description "Management port name (e.g. eth0)";
                    type string {
                        pattern 'eth([1-3][0-9]{3}|[1-9][0-9]{2}|[1-9][0-9]|[0-9])';
                    }
                }

                leaf speed {
                    type uint16 {
                        range "10|100|1000";
                    }

                    description
                        "Management port speed in Mbps.";
                }

                leaf autoneg {
                    description "Enable or disable auto-negotiation on the management port";
                    type string {
                        pattern "on|off";
                    }
                }

                leaf alias {
                    description "Alternative name for the management port";
                    type string;
                }

                leaf description {
                    description "User-defined description for the management port";
                    type string;
                }

                leaf mtu{
                    description "Maximum transmission unit size in bytes";
                    type uint16 {
                        range "1500..9216";
                    }
                    default 1500;
                }

                leaf admin_status {
                    description "Administrative state of the management port";
                    type stypes:admin_status;
                    default up;
                }

            } /* end of list MGMT_PORT_LIST */

        } /* end of container MGMT_PORT */

    } /* end of container sonic-mgmt_port */

} /* end of module sonic-mgmt_port */
