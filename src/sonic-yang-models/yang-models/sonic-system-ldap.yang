module sonic-system-ldap {
    yang-version 1.1;
    namespace "http://github.com/Azure/sonic-system-ldap";
    prefix ssys-ldap;

    import ietf-inet-types {
        prefix inet;
    }

    description "Lightweight Directory Access Protocol (LDAP) authentication configuration";

    revision 2023-10-01 {
        description "First Revision";
    }

    container sonic-system-ldap {

        container LDAP_SERVER {
            description "LDAP server list for remote user authentication.";
            list LDAP_SERVER_LIST {
                description "An LDAP server entry identified by hostname or IP address.";
                max-elements 8;
                key "hostname";

                leaf hostname {
                    type inet:host;
                    description
                        "LDAP server's Domain name or IP address (IPv4 or IPv6)";
                }

                leaf priority {
                    default 1;
                    type uint8 {
                        range "1..8" {
                            error-message "LDAP server priority must be 1..8";
                        }
                    }
                    description "Server selection priority; higher values are tried first.";
                }
            }
        }

        container LDAP {
            description "Global LDAP client configuration parameters.";

            container global {
                description "Global LDAP connection and authentication settings.";

                leaf bind_dn {
                    type string {
                        length "1..65";
                    }
                    description "Distinguished name used to bind to the LDAP server.";
                }

                leaf bind_password {
                    type string {
                        length "1..65";
                        pattern "[^ #,]*" {
                            error-message 'LDAP shared secret (Valid chars are ASCII printable except SPACE, "#", and ",")';
                        }
                    }
                    description "Password used to authenticate the bind DN with the LDAP server.";
                }

                leaf bind_timeout {
                    default 5;
                    type uint16 {
                        range "1..120" {
                            error-message "Ldap bind timeout must be 1..120";
                        }
                    }
                    description "Timeout in seconds for LDAP bind operations.";
                }

                leaf version {
                    default 3;
                    type uint16 {
                        range "1..3" {
                            error-message "Ldap version must be 1..3";
                        }
                    }
                    description "LDAP protocol version to use when communicating with the server.";
                }

                leaf base_dn {
                    type string {
                        length "1..65";
                    }
                    description "Base distinguished name for LDAP user searches.";
                }

                leaf port {
                    type inet:port-number;
                    default 389;
                    description "TCP port to communicate with LDAP server";
                }

                leaf timeout {
                    description "Timeout in seconds for LDAP search and query operations.";
                    type uint16 {
                        range "1..60" {
                            error-message "LDAP timeout must be 1..60";
                        }
                    }
                }
            } /* container global */
        } /* container LDAP  */
    }/* container sonic-system-ldap */
}/* end of module sonic-system-ldap */
