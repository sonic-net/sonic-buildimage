module sonic-fdb {

	yang-version 1.1;

	namespace "http://github.com/sonic-net/sonic-fdb";
	prefix fdb;

	import ietf-yang-types {
		prefix yang;
	}

	import sonic-vlan {
		prefix vlan;
	}

	import sonic-port {
		prefix port;
		revision-date 2019-07-01;
	}

	import sonic-portchannel {
		prefix lag;
	}

	description "FDB (static MAC) YANG module for SONiC OS";

	revision 2026-07-21 {
		description "Initial revision: static FDB (MAC) configuration.";
	}

	container sonic-fdb {

		container FDB {

			description "Static FDB (MAC) entries in CONFIG_DB. Programmed as
			             SAI static FDB by orchagent via APPL_DB FDB_TABLE.";

			list FDB_LIST {

				key "name mac";

				leaf name {
					description "VLAN of the static FDB entry.";
					type leafref {
						path "/vlan:sonic-vlan/vlan:VLAN/vlan:VLAN_LIST/vlan:name";
					}
				}

				leaf mac {
					description "Destination MAC address of the static FDB entry.";
					type yang:mac-address;
				}

				leaf port {
					description "Interface (port or PortChannel) the static MAC is bound to.";
					mandatory true;
					type union {
						type leafref {
							path "/port:sonic-port/port:PORT/port:PORT_LIST/port:name";
						}
						type leafref {
							path "/lag:sonic-portchannel/lag:PORTCHANNEL/lag:PORTCHANNEL_LIST/lag:name";
						}
					}
				}
			}
			/* end of list FDB_LIST */
		}
		/* end of container FDB */
	}
	/* end of container sonic-fdb */
}
