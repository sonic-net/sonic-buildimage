module sonic-bgp-common {
    namespace "http://github.com/sonic-net/sonic-bgp-common";
    prefix bgpcmn;
    yang-version 1.1;

    import sonic-types {
        prefix stypes;
    }

    import ietf-inet-types {
        prefix inet;
    }

    import sonic-port {
        prefix port;
    }

    import sonic-portchannel {
        prefix lag;
    }

  // Comment sonic-vlan import here until libyang back-links issue is resolved for VLAN leaf reference.
  //  import sonic-vlan {
  //      prefix vlan;
  //  }

    import sonic-loopback-interface {
        prefix lointf;
    }

    import sonic-routing-policy-sets {
        prefix rpolsets;
    }

    import sonic-route-map {
        prefix rmap;
    }

    import sonic-extension {
        prefix ext;
    }

    organization
        "SONiC";

    contact
        "SONiC";

    description
        "BGP common attributes for neighbors and peer groups";

    revision 2026-09-08 {
        description
            "Reject newline characters in template-based BGP neighbor descriptions.";
    }

    revision 2021-02-26 {
        description
            "Initial revision.";
    }

    typedef bgp_peer_type {
        type enumeration {
            enum internal {
                description "Internal peer";
            }
            enum external {
                description "External peer";
            }
        }
    }

    typedef bgp_tx_add_paths_type {
        type enumeration {
            enum tx_all_paths {
                description
                    "Send multiple path advertisements for an NLRI from
                    the neighbor or group";
            }
            enum tx_best_path_per_as {
                description
                    "Send only best path per AS advertisements for an NLRI from
                    the neighbor or group";
            }
        }
        description
            "Type to describe the add paths advertisement method.";
    }

    typedef bgp_community_type {
        type enumeration {
            enum standard {
                description "Standard communities";
            }

            enum extended {
                description "Extended communities";
            }

            enum both {
                description "Both standard and extended communities";
            }

            enum large {
                description "Large communities";
            }

            enum all {
                description "Standard, Extended and Large communities";
            }

            enum none {
                description "No community attribute";
            }
        }
        description
            "type describing variations of community attributes";
    }

    typedef sonic_bgp_direction {
        type enumeration {
            enum in {
                description
                    "Refers to information received from the BGP peer";
            }
            enum out {
                description
                    "Refers to information advertised to the BGP peer";
            }
        }
        description
            "Type to describe the direction";
    }

    typedef sonic_bgp_orf {
        type enumeration {
            enum send {
                description
                    "Capability to receive the outbound route filtering from this neighbor";
            }
            enum receive {
                description
                    "Capability to send the outbound route filtering to this neighbor";
            }
            enum both {
                description
                    "Capability to send and receive the outbound route filtering to/from this neighbor";
            }
        }
        description
            "Type to describe the BGP ORF(Outbound route filtering) capability";
    }

    grouping sonic-bgp-cmn {

        leaf local_asn {
            type uint32 {
                range "1..4294967295";
            }
            description "Local AS number";
        }

        leaf name {
            type string;
            description "Peer description";
        }

        leaf asn {
            type uint32 {
                range "1..4294967295";
            }
            description "Peer AS number";
        }

        leaf peer_type {
            type bgp_peer_type;
            description "BGP peer type internal/external";
        }

        leaf ebgp_multihop {
            type boolean;
            description "Enable eBGP multihop to allow peering with non-directly-connected external neighbors.";
        }

        leaf ebgp_multihop_ttl {
            type uint8 {
                range "1..255";
            }
            description "Maximum number of hops for eBGP multihop sessions.";
        }

        leaf auth_password {
            type string;
            description "MD5 authentication password for the BGP session.";
        }

        leaf keepalive {
            type uint16;
            description "BGP keepalive interval in seconds.";
        }

        leaf holdtime {
            type uint16;
            description "BGP hold time in seconds; session is reset if no keepalive is received within this period.";
        }

        leaf conn_retry {
            type uint16 {
                range "1..65535";
            }
            description "BGP connect retry timer in seconds.";
        }

        leaf min_adv_interval {
            type uint16 {
                range "0..600";
            }
            description "Minimum interval in seconds between sending BGP route updates to a peer.";
        }

        leaf local_addr {
            type union {
                type inet:ip-address;
                type leafref {
                    path "/port:sonic-port/port:PORT/port:PORT_LIST/port:name";
                }
                type leafref {
                    path "/lag:sonic-portchannel/lag:PORTCHANNEL/lag:PORTCHANNEL_LIST/lag:name";
                }
                // Comment VLAN leaf reference here until libyang back-links issue is resolved and use VLAN string pattern
                //type leafref {
                //    path "/vlan:sonic-vlan/vlan:VLAN/vlan:VLAN_LIST/vlan:name";
                //}
                type leafref {
                    path "/lointf:sonic-loopback-interface/lointf:LOOPBACK_INTERFACE/lointf:LOOPBACK_INTERFACE_LIST/lointf:name";
                }
                type string {
                    pattern 'Vlan([0-9]{1,3}|[1-3][0-9]{3}|[4][0][0-8][0-9]|[4][0][9][0-4])';
                }
            }
            description "Local source address or interface name to use for connection.";
        }

        leaf passive_mode {
            type boolean;
            description "Wait for the peer to initiate the BGP session instead of actively connecting.";
        }

        leaf capability_ext_nexthop {
            type boolean;
            description "Advertise extended nexthop capability to allow IPv4 prefixes over IPv6 nexthops.";
        }

        leaf disable_ebgp_connected_route_check {
            type boolean;
            description "Disable the check that an eBGP peer's address must be a connected route.";
            //ext:custom-validation ValidateDisableConnectedCheck;
        }

        leaf enforce_first_as {
            type boolean;
            description "Require the first AS in the AS path to be the peer's AS number for eBGP sessions.";
        }

        leaf solo_peer {
            type boolean;
            description "Place this peer in its own update group to prevent route sharing with other peers.";
        }

        leaf ttl_security_hops {
            type uint8 {
                range 1..254;
            }
            description "Maximum number of hops expected for the BGP TTL security mechanism (GTSM).";
        }

        leaf bfd {
            type boolean;
            description "Enable Bidirectional Forwarding Detection (BFD) for rapid link failure detection on this peer.";
        }

        leaf bfd_check_ctrl_plane_failure {
            type boolean;
            description "Trigger BGP session reset when a BFD control plane failure is detected.";
        }

        leaf capability_dynamic {
            type boolean;
            description "Advertise dynamic capability";
        }

        leaf dont_negotiate_capability {
            type boolean;
            description "Do not perform capability negotiation";
        }

        leaf enforce_multihop {
            type boolean;
            description "Enforce EBGP neighbors perform multihop";
        }

        leaf override_capability {
            type boolean;
            description "Override capability negotiation result";
        }

        leaf peer_port {
            type uint16;
            description "Peer port number";
        }

        leaf shutdown_message {
            type string {
                length "1..127";
            }
            description "Human-readable message sent in the BGP NOTIFICATION when administratively shutting down the peer.";
        }

        leaf strict_capability_match {
            type boolean;
            //ext:custom-validation ValidateStrictAndOverRideCapability;
            description "Require exact match of capabilities; tear down session if capabilities do not match.";
        }

        leaf admin_status {
            type stypes:admin_status;
            description "Administrative status to enable or disable this BGP peer.";
        }

        leaf local_as_no_prepend {
            type boolean;
            description "Do not prepend the local AS number to updates received from eBGP peers.";
        }

        leaf local_as_replace_as {
            type boolean;
            description "Replace the real AS number with the local AS number in outbound updates.";
        }
    }


    grouping sonic-bgp-cmn-af {

        leaf afi_safi {
            type string;
            description "Address family";
        }

        leaf admin_status {
            type stypes:admin_status;
            description "Indicates address family active/inactive status";
        }

        leaf send_default_route {
            type boolean;
            description "Originate a default route to this neighbor.";
        }

        leaf default_rmap {
            type leafref {
                path "/rmap:sonic-route-map/rmap:ROUTE_MAP_SET/rmap:ROUTE_MAP_SET_LIST/rmap:name";
            }
            description "Route map applied when originating a default route to this neighbor.";
        }

        leaf max_prefix_limit {
            type uint32;
            description "Maximum number of prefixes accepted from this neighbor before taking action.";
        }

        leaf max_prefix_warning_only {
            type boolean;
            description "Only log a warning instead of tearing down the session when the maximum prefix limit is exceeded.";
        }

        leaf max_prefix_warning_threshold {
            type uint8 {
                range "1..100";
            }
            description "Percentage of the maximum prefix limit at which a warning is generated.";
        }

        leaf max_prefix_restart_interval {
            type uint16 {
                range "1..65535";
            }
            description "Time in seconds to wait before re-establishing the session after a max-prefix limit shutdown.";
        }

        leaf-list route_map_in {
            type leafref {
                path "/rmap:sonic-route-map/rmap:ROUTE_MAP_SET/rmap:ROUTE_MAP_SET_LIST/rmap:name";
            }
            ordered-by user;
            description "Route-map filter for incoming routes";
            max-elements 1;
        }

        leaf-list route_map_out {
            type leafref {
                path "/rmap:sonic-route-map/rmap:ROUTE_MAP_SET/rmap:ROUTE_MAP_SET_LIST/rmap:name";
            }
            ordered-by user;
            description "Route-map filter for outgoing routes";
            max-elements 1;
        }

        leaf soft_reconfiguration_in {
            type boolean;
            description "Enable storing of inbound updates to allow route refresh without resetting the session.";
        }

        leaf unsuppress_map_name {
            type leafref {
                path "/rmap:sonic-route-map/rmap:ROUTE_MAP_SET/rmap:ROUTE_MAP_SET_LIST/rmap:name";
            }
            description "Route map used to selectively unsuppress suppressed routes to this neighbor.";
        }

        leaf rrclient {
            type boolean;
            description "Configure this neighbor as a route reflector client.";
        }

        leaf weight {
            type uint16 {
                range 0..65535;
            }
            description "Default weight assigned to routes received from this neighbor for best-path selection.";
        }

        leaf as_override {
            type boolean;
            description "Replace the peer AS number with the local AS in outbound updates to prevent loops in dual-homed networks.";
        }

        leaf send_community {
            type bgp_community_type;
            description "Send Community attribute to this neighbor";
        }

        leaf tx_add_paths {
            type bgp_tx_add_paths_type;
            description "Advertise all paths or best path per AS using add path";
        }

        leaf unchanged_as_path {
            type boolean;
            description "Propagate the AS path attribute unchanged to this neighbor.";
        }

        leaf unchanged_med{
            type boolean;
            description "Propagate the MED attribute unchanged to this neighbor.";
        }

        leaf unchanged_nexthop {
            type boolean;
            description "Propagate the nexthop attribute unchanged to this neighbor.";
        }

        leaf filter_list_in {
            type leafref {
                path "/rpolsets:sonic-routing-policy-sets/rpolsets:AS_PATH_SET/rpolsets:AS_PATH_SET_LIST/rpolsets:name";
            }
            description "AS-path access list name for filtering inbound routes.";
        }

        leaf filter_list_out {
            type leafref {
                path "/rpolsets:sonic-routing-policy-sets/rpolsets:AS_PATH_SET/rpolsets:AS_PATH_SET_LIST/rpolsets:name";
            }
            description "AS-path access list name for filtering outbound routes.";
        }

        leaf nhself {
            type boolean;
            description "Nexthop is self, no nexthop calculation";
        }

        leaf nexthop_self_force {
            type boolean;
            description "Force nexthop to be self for reflected routes";
        }

        leaf prefix_list_in {
            type leafref {
                path "/rpolsets:sonic-routing-policy-sets/rpolsets:PREFIX_SET/rpolsets:PREFIX_SET_LIST/rpolsets:name";
            }
            description "Prefix list name for filtering inbound routes.";
        }

        leaf prefix_list_out {
            type leafref {
                path "/rpolsets:sonic-routing-policy-sets/rpolsets:PREFIX_SET/rpolsets:PREFIX_SET_LIST/rpolsets:name";
            }
            description "Prefix list name for filtering outbound routes.";
        }

        leaf remove_private_as_enabled {
            type boolean;
            description "Remove private AS numbers from the AS path in outbound updates.";
        }

        leaf replace_private_as {
            type boolean;
            description "Replace private AS numbers with the local AS number in outbound updates.";
        }

        leaf remove_private_as_all {
            type boolean;
            description "Remove all private AS numbers (including in the middle of the path) from outbound updates.";
        }

        leaf allow_as_in {
            type boolean;
            description "Accept inbound routes even when the local AS number appears in the AS path.";
        }

        leaf allow_as_count {
            type uint8;
            description "Maximum number of times the local AS number may appear in a received AS path.";
        }

        leaf allow_as_origin {
            type boolean;
            description "Accept routes that originated from the local AS.";
        }

        leaf cap_orf {
            type sonic_bgp_orf;
            description "Outbound Route Filtering (ORF) prefix-list capability to negotiate with this neighbor.";
        }

        leaf route_server_client {
            type boolean;
            description "Configure this neighbor as a route server client, disabling attribute modification.";
        }
    }

    grouping sonic-bgp-cmn-neigh {
        leaf asn {
            type uint32 {
                range "0..4294967295";
            }
            description "Peer AS number.";
        }

        leaf holdtime {
            type uint16;
            description "BGP hold time in seconds; session is reset if no keepalive is received within this period.";
        }

        leaf keepalive {
            type uint16;
            description "BGP keepalive interval in seconds.";
        }

        leaf local_addr {
            type inet:ip-address;
            description "Local source address to use for the BGP session.";
        }

        leaf name {
            type string {
                pattern '[^\n\r]*';
            }
            description "Human-readable description text for this BGP peer.";
        }

        leaf nhopself {
            type uint8 {
                range "0..1";
            }
            description "Set nexthop to self for routes advertised to this peer.";
        }

        leaf rrclient {
            type uint8 {
                range "0..1";
            }
            description "Configure this neighbor as a route reflector client.";
        }

        leaf admin_status {
            type stypes:admin_status;
            description "Administrative status to enable or disable this BGP peer.";
        }

        leaf address_family {
            type string {
                pattern "v4|v6|both";
            }
            default "both";
            description "Address families to activate for this unnumbered BGP peer: v4, v6, or both.";
        }
    }
}
