module sonic-isis {

    namespace "http://github.com/Azure/sonic-isis";

    prefix "s-isis";

    yang-version 1.1;

    import sonic-vrf {
        prefix vrf;
    }

    import sonic-port {
        prefix port;
    }

    import sonic-portchannel {
        prefix lag;
    }

    import sonic-loopback-interface {
        prefix lo;
    }

    organization
        "SONiC";

    contact
        "SONiC";

    description
        "Intermediate System to Intermediate System Protocol";

    revision 2023-03-16 {
        description "Initial revision.";
    }

    identity AUTH_MODE {
        description
            "Base identify to define the authentication mode";
    }

    identity TEXT {
        base AUTH_MODE;
            description
                "Simple Text Authentication";
        reference "RFC1195";
    }

    identity MD5 {
        base AUTH_MODE;
            description
                "HMAC-MD5 Authentication";
        reference "RFC5304";
    }

    typedef circuit-type {
        type enumeration {
            enum POINT_TO_POINT {
                description
                    "This enum describes a point-to-point interface";
            }
            enum BROADCAST {
                description
                    "This enum describes a broadcast interface";
            }
        }
        description
            "This type defines IS-IS interface types ";
    } 

    typedef net {
        type string {
            pattern '[a-fA-F0-9]{2}(\.[a-fA-F0-9]{4}){3,9}\.[a-fA-F0-9]{2}';
            }
        description
            "This type defines OSI NET address. A NET should should be in
            the form xx.yyyy.yyyy.yyyy.00 with up to 9 sets of yyyy.";
    }

    typedef level-type {
        type enumeration {
            enum LEVEL_1 {
                description
                    "This enum describes IS-IS level 1";
            }
            enum LEVEL_2 {
                description
                    "This enum describes IS-IS level 2";
            }
            enum LEVEL_1_2 {
                description
                    "This enum describes IS-IS level 1-2";
            }
        }
        description
            "This type defines IS-IS level types";
    }

    grouping isis-authentication {
        leaf authentication_key {
            type string {
                length "1..254";
            }
            must "(../authentication_type or not(../authentication_key))" {
                error-message
                    "If authentication_key is specified, then authentication_type must also be specified.";
            }
            description
                "Authentication password.";
        }

        leaf authentication_type {
            type identityref {
                base AUTH_MODE;
            }
            must "(../authentication_key or not(../authentication_type))" {
                error-message
                    "If authentication_type is specified, then authentication_key must also be specified.";
            }
            description
                "This grouping defines keychain configuration type (TEXT, MD5).";
        }
    }


    container sonic-isis {

        container ISIS_GLOBAL {

            list ISIS_GLOBAL_LIST {

                max-elements "1";

                key "vrf_name instance";

                leaf vrf_name {
                    type union {
                        type string {
                            pattern "default";
                        }
                        type leafref {
                            path "/vrf:sonic-vrf/vrf:VRF/vrf:VRF_LIST/vrf:name";
                        }
                    }
                    must "not(../../../ISIS_LEVELS/ISIS_LEVELS_LIST) or (../../../ISIS_LEVELS/ISIS_LEVELS_LIST[vrf_name=current()/../vrf_name])" {
                        error-message
                            "The value of ISIS_GLOBAL 'vrf_name' must be the same as 'vrf_name' in ISIS_LEVELS.";
                    }
                    description 
                        "VRF name";
                }

                leaf instance {
                    type string;
                    description
                        "The identifier for this instance of IS-IS. Area-tag";
                    must "not(../../../ISIS_LEVELS/ISIS_LEVELS_LIST) or (../../../ISIS_LEVELS/ISIS_LEVELS_LIST[instance=current()/../instance])" {
                        error-message
                            "The value of ISIS_GLOBAL 'instance' must be the same as 'instance' in ISIS_LEVELS.";
                    }
                }

                leaf net { 
                    type net; 
                    description
                        "IS-IS OSI network entity title (NET) address.";
                }

                leaf level_capability {
                    type level-type;
                    default "LEVEL_1_2";
                    description
                        "IS-IS level capability (LEVEL_1, LEVEL_2, LEVEL_1_2).";
                  }

                leaf dynamic_hostname {
                    type boolean;
                    default "true";
                    description
                        "Dynamic hostname support for IS-IS.";
                }

                leaf attach_send {
                    type boolean;
                    default "true";
                    description
                        "For an L1 or L2 router, attached bits are sent in an LSP when set to true.";
                }

                leaf attach_receive_ignore {
                    type boolean;
                    default "false";
                    description
                        "For an L1 router, attached bits received in an LSP create a default route when set to false";
                }

                leaf set_overload_bit {
                    type boolean;
                    default "false";
                    description
                        "Administratively enable the overload bit.";
                }

                leaf lsp_mtu_size {
                    type uint16 {
                        range "128..4352";
                    }
                    default "1497";
                    description
                        "LSP MTU.";
                }

                leaf spf_init_delay {
                    type uint16 {
                        range "0..60000";
                    }
                    units "msec";
                    must "../spf_short_delay and ../spf_long_delay and ../spf_hold_down and ../spf_time_to_learn or not(../spf_init_delay)" {
                        error-message
                            "SPF init delay must only be specified if all other SPF parameters are specified";
                    }
                    description
                        "Delay used during QUIET state";
                }

                leaf spf_short_delay {
                    type uint16 {
                        range "0..60000";
                    }
                    units "msec";
                    must "../spf_init_delay and ../spf_long_delay and ../spf_hold_down and ../spf_time_to_learn or not(../spf_short_delay)" {
                        error-message
                            "SPF short delay must only be specified if all other SPF parameters are specified";
                    }
                    description
                        "Delay used during SHORT_WAIT state";
                }

                leaf spf_long_delay {
                    type uint16 {
                        range "0..60000";
                    }
                    units "msec";
                    must "../spf_init_delay and ../spf_short_delay and ../spf_hold_down and ../spf_time_to_learn or not(../spf_long_delay)" {
                        error-message
                            "SPF long delay must only be specified if all other SPF parameters are specified";
                    }
                    description
                        "Delay used during LONG_WAIT state";
                }

                leaf spf_hold_down {
                    type uint16 {
                        range "0..60000";
                    }
                    units "msec";
                    must "../spf_init_delay and ../spf_short_delay and ../spf_long_delay and ../spf_time_to_learn or not(../spf_hold_down)" {
                        error-message
                            "SPF hold down must only be specified if all other SPF parameters are specified";
                    }
                    description
                        "Period of time without IGP events before considering IGP stable";
                }

                leaf spf_time_to_learn {
                    type uint16 {
                        range "0..60000";
                    }
                    units "msec";
                    must "../spf_init_delay and ../spf_short_delay and ../spf_long_delay and ../spf_hold_down or not(../spf_time_to_learn)" {
                        error-message
                            "SPF time_to_learn must only be specified if all other SPF parameters are specified";
                    }
                    description
                        "Maximum time needed to learn all of the events related to a failure";
                }

                leaf log_adjacency_changes {
                    type boolean;
                    default "false";
                    description
                        "Log changes to this instance's IS-IS adjacencies.";
                }

            } // list ISIS_GLOBAL_LIST

        } // container ISIS_GLOBAL

        container ISIS_LEVELS {

            list ISIS_LEVELS_LIST {

                description
                    "Configuration parameters related to a particular level within the
                    IS-IS protocol instance";

                key "vrf_name instance level_number";

                leaf vrf_name {
                    type union {
                        type string {
                            pattern "default";
                        }
                        type leafref {
                            path "/vrf:sonic-vrf/vrf:VRF/vrf:VRF_LIST/vrf:name";
                        }
                    }
                    must "not(../../../ISIS_GLOBAL/ISIS_GLOBAL_LIST) or (../../../ISIS_GLOBAL/ISIS_GLOBAL_LIST[vrf_name=current()/../vrf_name])" {
                        error-message
                            "The value of ISIS_LEVELS 'vrf_name' must be the same as 'vrf_name' in ISIS_GLOBAL.";
                    }
                    description
                        "VRF name";
                }

                leaf instance {
                    type string;
                    must "not(../../../ISIS_GLOBAL/ISIS_GLOBAL_LIST) or (../../../ISIS_GLOBAL/ISIS_GLOBAL_LIST[instance=current()/../instance])" {
                        error-message 
                            "The value of ISIS_LEVELS 'instance' must be the same as 'instance' in ISIS_GLOBAL.";
                    }
                    description
                        "The identifier for this instance of IS-IS. Area-tag";
                }

                leaf level_number {
                    type uint8 {
                        range "1..2";
                    }
                    description
                        "IS-IS level number (1..2).";
                }

                leaf lsp_refresh_interval {
                    type uint16;
                    units "seconds";
                    default "900";
                    description
                        "LSP refresh interval.";
                }

                leaf lsp_maximum_lifetime {
                    type uint16 {
                        range "350..65535";
                    }
                    units "seconds";
                    must "(. >= ../lsp_refresh_interval + 300)" {
                        error-message
                            "lsp_maximum_lifetime must be at least 300 seconds greater than lsp_refresh_interval";
                    }
                    default "1200";
                    description
                        "Maximum LSP lifetime.";
                }

                leaf lsp_generation_interval {
                    type uint16 {
                        range "1..120";
                    }
                    units "seconds";
                    must "(. < ../lsp_refresh_interval)" {
                        error-message
                            "lsp_generation_interval must be greater than lsp_refresh_interval";
                    }
                    default "30";
                    description
                        "Minimum time before an LSP retransmissions.";
                }

                leaf spf_minimum_interval {
                    type uint16 {
                        range "1..120";
                    }
                    units "seconds";
                    default "1";
                    description
                        "Minimum time between consecutive SPFs.";
                }

            } // list ISIS_LEVELS_LIST

        } // container ISIS_LEVELS

        container ISIS_INTERFACE {

            list ISIS_INTERFACE_LIST {

                description
                    "Configuration parameters related to a particular interface within the
                    IS-IS protocol instance";

                key "instance ifname";

                leaf instance {
                    type union {
                        type leafref {
                            path "../../../ISIS_GLOBAL/ISIS_GLOBAL_LIST/instance";
                        }
                        type leafref {
                            path "../../../ISIS_LEVELS/ISIS_LEVELS_LIST/instance";
                        }
                    }
                    description
                        "The identifier for this instance of IS-IS. Area-tag";
                }

                leaf ifname {
                    type union {
                        type leafref {
                            path "/port:sonic-port/port:PORT/port:PORT_LIST/port:name";
                        }
                        type leafref {
                            path "/lag:sonic-portchannel/lag:PORTCHANNEL/lag:PORTCHANNEL_LIST/lag:name";
                        }
                        type leafref {
                            path "/lo:sonic-loopback-interface/lo:LOOPBACK_INTERFACE/lo:LOOPBACK_INTERFACE_LIST/lo:name";
                        }
                    }
                    description
                        "Interface for which IS-IS configuration is to be applied.";
                }

                leaf ipv4_routing_instance {
                    type leafref {
                        path "../../../ISIS_GLOBAL/ISIS_GLOBAL_LIST/instance";
                    }
                    description
                        "Routing IS-IS IPv4 traffic over this interface for the given instance.";
                }

                leaf ipv6_routing_instance {
                    type leafref {
                        path "../../../ISIS_GLOBAL/ISIS_GLOBAL_LIST/instance";
                    }
                    description
                        "Routing IS-IS IPv6 traffic over this interface for the given instance.";
                }

                leaf passive {
                    type boolean;
                    default "false";
                    description
                        "When set to true, the referenced interface is a passive interface
                        such that it is not eligible to establish adjacencies with other
                        systems, but is advertised into the IS-IS topology.";
                }

                leaf hello_padding {
                    type boolean; 
                    default "true";
                    description
                        "When true, padding is added to IS-IS hello PDUs.";
                }

                leaf network_type {
                    type circuit-type;
                    description
                        "IS-IS interface type (POINT_TO_POINT, BROADCAST).";
                }

                leaf enable_bfd {
                    type boolean;
                    default "false";
                    description
                        "Monitor IS-IS peers on this interface.";
                }

                leaf bfd_profile {
                    type string;
                    description
                        "Set BFD to use a pre-configured profile.";
                }

                leaf metric {
                    type uint32 {
                        range "0..16777215";
                    }
                    default "0";
                    description
                        "The metric value of this interface.";
                }

                leaf csnp_interval {
                    type uint16 {
                        range "1..600";
                    }
                    units "seconds";
                    default "10";
                    description
                        "Complete Sequence Number PDU (CSNP) generation interval.";
                }

                leaf psnp_interval {
                    type uint16 {
                        range "1..120";
                    }
                    units "seconds";
                    default "2";
                    description
                        "Partial Sequence Number PDU (PSNP) generation interval.";
                }

                leaf hello_interval {
                    type uint32 {
                        range "1..600";
                    }
                    units "seconds";
                    default "3";
                    description
                        "Hello interval between consecutive hello messages. Interval will depend on multiplier.";
                }

                leaf hello_multiplier {
                    type uint16 {
                        range "2..100";
                    }
                    default "10";
                    description
                        "Multiplier for the hello holding time.";
                }

                uses isis-authentication; 

            }  // list ISIS_INTERFACE

        } // container ISIS_INTERFACE

    } // container sonic-isis

} //module sonic-isis
