module sonic-fast-linkup {
  yang-version 1.1;
  namespace "http://github.com/sonic-net/sonic-fast-linkup";
  prefix sfl;

  organization "SONiC";
  contact "SONiC";
  description
    "SWITCH_FAST_LINKUP global configuration.";

  revision 2025-10-20 {
    description "Initial revision.";
  }

  container sonic-fast-linkup {
    container SWITCH_FAST_LINKUP {
      description "Global fast link-up profile configuration for reduced link initialization time";

      container GLOBAL {
        description "Global fast link-up parameters";

        leaf polling_time {
          type uint16;
          description "Polling time in seconds";
        }
        leaf guard_time {
          type uint8;
          description "Guard time in seconds";
        }
        leaf ber_threshold {
          type uint8;
          description "BER threshold exponent (e.g., 12 for 1e-12)";
        }
      }
      /* end of container GLOBAL */
    }
    /* end of container SWITCH_FAST_LINKUP */
  }
}
