module sonic-buffer-queue {
    namespace "http://github.com/sonic-net/sonic-buffer-queue";
    prefix bqueue;

    import sonic-port {
        prefix prt;
    }

    import sonic-buffer-profile {
        prefix bpf;
    }

    import sonic-device_metadata {
        prefix sdm;
    }

    import sonic-types {
        prefix stypes;
    }

    organization
        "SONiC";

    contact
        "SONiC";

    description
        "Egress queue buffer configuration per port.";

    revision 2021-07-01 {
        description
            "Initial revision.";
    }

    container sonic-buffer-queue {

        container BUFFER_QUEUE {

            description "Configures buffer profiles for egress queues on ports.";

            list BUFFER_QUEUE_LIST {

                description "Buffer queue entry for a non-VOQ port.";
                when "not(/sdm:sonic-device_metadata/sdm:DEVICE_METADATA/sdm:localhost/sdm:switch_type) or
                    (/sdm:sonic-device_metadata/sdm:DEVICE_METADATA/sdm:localhost/sdm:switch_type!='voq')";

                key "port qindex";

                leaf port {
                    type leafref {
                        path "/prt:sonic-port/prt:PORT/prt:PORT_LIST/prt:name";
                    }
                    description "Port on which the egress queue buffer is configured.";
                }

                leaf qindex {
                    type string {
                        pattern "(1[0-5]|[0-9])((-)(1[0-5]|[0-9]))?"{
                            error-message "Invalid Q-index";
                            error-app-tag qindex-invalid;
                        }
                    }
                    description "Egress queue index or range (e.g. 0-3) on the port.";
                }

                leaf profile {
                    default 0;
                    type leafref {
                        path "/bpf:sonic-buffer-profile/bpf:BUFFER_PROFILE/bpf:BUFFER_PROFILE_LIST/bpf:name";
                    }
                    description "Buffer profile applied to this egress queue.";
                }

            }
            list VOQ_BUFFER_QUEUE_LIST {

                description "Buffer queue entry for a VOQ chassis port.";
                when "boolean(/sdm:sonic-device_metadata/sdm:DEVICE_METADATA/sdm:localhost/sdm:switch_type) and
                    (/sdm:sonic-device_metadata/sdm:DEVICE_METADATA/sdm:localhost/sdm:switch_type='voq')";

                key "hostname asic_name port qindex";

                leaf hostname {
                    type stypes:hostname;
                    description "VOQ chassis hostname owning this port.";
                }

                leaf asic_name {
                    type stypes:asic_name;
                    description "ASIC instance name within the VOQ chassis.";
                }

                leaf port {
                    type string {
                        length 1..128;
                    }
                    description "Port name on the VOQ chassis linecard.";
                }

                leaf qindex {
                    type string {
                        pattern "(1[0-5]|[0-9])((-)(1[0-5]|[0-9]))?"{
                            error-message "Invalid Q-index";
                            error-app-tag qindex-invalid;
                        }
                    }
                    description "Egress queue index or range (e.g. 0-3) on the port.";
                }

                leaf profile {
                    default 0;
                    type leafref {
                        path "/bpf:sonic-buffer-profile/bpf:BUFFER_PROFILE/bpf:BUFFER_PROFILE_LIST/bpf:name";
                    }
                    description "Buffer profile applied to this egress queue.";
                }

            }
        }
    }
}
