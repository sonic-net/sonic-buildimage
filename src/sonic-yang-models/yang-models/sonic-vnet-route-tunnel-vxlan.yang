module sonic-vnet-route-tunnel-vxlan {

    yang-version 1.1;

    namespace "http://github.com/sonic-net/sonic-vnet-route-tunnel-vxlan";
    prefix todo;

    import ietf-inet-types {
        prefix inet;
    }

    import ietf-yang-types {
        prefix yang;
    }

    import sonic-types {
        prefix stypes;
    }

    import sonic-vxlan {
        prefix svxlan;
    }

    organization
        "SONiC";

    contact
        "SONiC";

    description
        "VNET_ROUTE_TUNNEL YANG Module for SONiC OS";

    revision 2025-02-20 {
        description
            "Initial revision.";
    }

    container sonic-vnet-route-tunnel-vxlan {
        
        container VNET_ROUTE_TUNNEL {

            description "app db VNET_ROUTE_TUNNEL table";

            list VNET_ROUTE_TUNNEL_LIST {

                key "name";
                unique vxlanid;

                leaf name {
                    type string {
                        pattern "[^:]+:((([0-9]|[1-9][0-9]|1[0-9][0-9]|2[0-4][0-9]|25[0-5])\\.){3}([0-9]|[1-9][0-9]|1[0-9][0-9]|2[0-4][0-9]|25[0-5])/(([0-9])|([1-2][0-9])|(3[0-2])))";
                    }
                    description "Combined key of vnet_name:prefix (e.g., 'Vnet1-1:10.0.0.0/24')";
                }
                
                leaf endpoint {
                    type inet:ipv4-address;
                    mandatory true;
                    description "Host VM IP address (endpoint of the tunnel)";
                }

                leaf mac_address {
                    type yang:mac-address;
                    description "Inner dest mac in encapsulated packet";
                }

                leaf vxlanid {
                    type stypes:vnid_type;
                    description "A valid and unique vni value in encapsulated packet";
                }
            }
        }
    }
}
