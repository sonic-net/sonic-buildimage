module sonic-dhcp-server-ipv4 {

    yang-version 1.1;

    namespace "http://github.com/sonic-net/sonic-dhcp-server-ipv4";

    prefix dhcp-server-ipv4;

    import ietf-inet-types {
        prefix inet;
    }

    import sonic-types {
        prefix stypes;
    }

    // Comment sonic-vlan import here until libyang back-links issue is resolved for VLAN leaf reference.
    // import sonic-vlan {
    //     prefix vlan;
    // }

    import sonic-port {
        prefix port;
    }

    import sonic-portchannel {
        prefix lag;
    }

    import sonic-smart-switch {
        prefix smartswitch;
    }

    description "DHCP_SERVER_IPV4 YANG module for SONiC OS";

    revision 2026-08-22 {
        description "Add match condition based DHCPv4 address assignment";
    }

    revision 2023-07-19 {
        description "Initial version";
    }

    container sonic-dhcp-server-ipv4 {
        container DHCP_SERVER_IPV4 {

            description "DHCPv4 server configuration per interface";

            list DHCP_SERVER_IPV4_LIST {

                description "DHCPv4 server instance for a specific interface";

                key "name";

                leaf name {
                    description "Interface name for DHCP server";
                    type union {
                        // Comment VLAN leaf reference here until libyang back-links issue is resolved and use VLAN string pattern
                        // type leafref {
                        //     path "/vlan:sonic-vlan/vlan:VLAN/vlan:VLAN_LIST/vlan:name";
                        // }
                        type string {
                            pattern 'Vlan([0-9]{1,3}|[1-3][0-9]{3}|[4][0][0-8][0-9]|[4][0][9][0-4])';
                        }
                        type leafref {
                            path "/smartswitch:sonic-smart-switch/smartswitch:MID_PLANE_BRIDGE/smartswitch:GLOBAL/smartswitch:bridge";
                        }
                    }
                }

                leaf gateway {
                    description "Gateway IP for DHCP server";
                    type inet:ipv4-address;
                }

                leaf lease_time {
                    description "Lease time of DHCP IP in second";
                    mandatory true;
                    type uint32 {
                        range "1..4294967295";
                    }
                }

                leaf mode {
                    description "Mode of assigning IP";
                    mandatory true;
                    type enumeration {
                        enum PORT;
                    }
                }

                leaf netmask {
                    description "Subnet mask value for DHCP server";
                    mandatory true;
                    type inet:ipv4-address-no-zone;
                }

                leaf-list customized_options {
                    description "Customized options list";
                    type leafref {
                        path "/dhcp-server-ipv4:sonic-dhcp-server-ipv4/dhcp-server-ipv4:DHCP_SERVER_IPV4_CUSTOMIZED_OPTIONS/dhcp-server-ipv4:DHCP_SERVER_IPV4_CUSTOMIZED_OPTIONS_LIST/dhcp-server-ipv4:name";
                    }
                    ordered-by user;
                }

                leaf state {
                    description "State of DHCP server";
                    mandatory true;
                    type stypes:admin_mode;
                }
            }
            /* end of DHCP_SERVER_IPV4_LIST */
        }
        /* end of DHCP_SERVER_IPV4 container */

        container DHCP_SERVER_IPV4_CUSTOMIZED_OPTIONS {

            description "Customized DHCP option definitions for DHCPv4 server";

            list DHCP_SERVER_IPV4_CUSTOMIZED_OPTIONS_LIST {

                description "A customized DHCP option with ID, type, and value";

                key "name";

                leaf name {
                    description "Name of customized option";
                    type string {
                        length 1..255 {
                            error-message "Invalid length for the customized options name";
                        }
                    }
                }

                leaf id {
                    description "DHCP option ID number";
                    mandatory true;
                    type uint8 {
                        range "1..254";
                    }
                }

                leaf type {
                    description "Type of customized option, for standard DHCP option, this field is invalid";
                    type enumeration {
                        enum string;
                        enum ipv4-address;
                        enum uint8;
                        enum uint16;
                        enum uint32;
                    }
                }

                leaf value {
                    description "Value of customized option";
                    mandatory true;
                    type union {
                        type string {
                            length 0..255;
                        }
                        type inet:ipv4-address;
                        type uint8;
                        type uint16;
                        type uint32;
                    }
                }

                leaf always_send {
                    description "Always send option or not";
                    type boolean;
                    default true;
                }
            }
            /* end of DHCP_SERVER_IPV4_CUSTOMIZED_OPTIONS_LIST */
        }
        /* end of DHCP_SERVER_IPV4_CUSTOMIZED_OPTIONS container */

        container DHCP_SERVER_IPV4_RANGE {

            description "Named IPv4 address ranges for DHCP IP allocation";

            list DHCP_SERVER_IPV4_RANGE_LIST {

                description "An IPv4 address range defined by one or two IP addresses";

                key "name";

                leaf name {
                    description "Name of IP range";
                    type string {
                        length 1..255 {
                            error-message "Invalid length for the IP range name";
                        }
                    }
                }

                leaf-list range {
                    description "Range of IPs";
                    type inet:ipv4-address;
                    ordered-by user;
                }

                must "((count(range) <= 2) and (count(range) >= 1))";
            }
            /* end of DHCP_SERVER_IPV4_RANGE_LIST */
        }
        /* end of DHCP_SERVER_IPV4_RANGE */

        container DHCP_SERVER_IPV4_PORT {

            description "Port-based DHCP IP assignment binding ports to addresses or ranges";

            list DHCP_SERVER_IPV4_PORT_LIST {

                description "A port-to-IP assignment for a DHCP server interface";

                key "name port";

                leaf name {
                    description "Name of DHCP interface";
                    type leafref {
                        path "/dhcp-server-ipv4:sonic-dhcp-server-ipv4/dhcp-server-ipv4:DHCP_SERVER_IPV4/dhcp-server-ipv4:DHCP_SERVER_IPV4_LIST/dhcp-server-ipv4:name";
                    }
                }

                leaf port {
                    description "Interface under DHCP interface";
                    type union {
                        type leafref {
                            path "/port:sonic-port/port:PORT/port:PORT_LIST/port:name";
                        }
                        type leafref {
                            path "/lag:sonic-portchannel/lag:PORTCHANNEL/lag:PORTCHANNEL_LIST/lag:name";
                        }
                        type leafref {
                            path "/smartswitch:sonic-smart-switch/smartswitch:DPUS/smartswitch:DPUS_LIST/smartswitch:midplane_interface";
                        }
                    }
                }

                leaf-list ips {
                    description "Assigned IPs";
                    must "(not(boolean(../ranges)))"{
                        error-message "Statement of 'ips' and 'ranges' cannot both exist";
                    }
                    type inet:ipv4-address;
                    ordered-by user;
                }

                leaf-list ranges {
                    description "IP ranges";
                    must "(not(boolean(../ips)))"{
                        error-message "Statement of 'ips' and 'ranges' cannot both exist";
                    }
                    type leafref {
                        path "/dhcp-server-ipv4:sonic-dhcp-server-ipv4/dhcp-server-ipv4:DHCP_SERVER_IPV4_RANGE/dhcp-server-ipv4:DHCP_SERVER_IPV4_RANGE_LIST/dhcp-server-ipv4:name";
                    }
                    ordered-by user;
                }
            }
            /* end of DHCP_SERVER_IPV4_PORT_LIST */
        }
        /* end of DHCP_SERVER_IPV4_PORT container */

        container DHCP_SERVER_IPV4_MATCH {

            description "Named DHCPv4 packet match conditions";

            list DHCP_SERVER_IPV4_MATCH_LIST {

                description "A named exact-match condition for conditional DHCP IP assignment";

                key "name";

                leaf name {
                    description "Name of match condition";
                    type string {
                        length 1..255 {
                            error-message "Invalid length for match condition name";
                        }
                        /* '|' is the Config DB key separator, so a name containing it
                           cannot be recovered when the table key is split back into
                           its YANG key leafs. ',' is the Config DB leaf-list separator:
                           DHCP_SERVER_IPV4_BINDING/matches is serialised as a single
                           'matches@' string joined on ',', so a name containing one
                           would be read back as two separate, non-existent references. */
                        pattern "[^|,]*" {
                            error-message "Match condition name must not contain '|' or ','";
                        }
                        /* Config DB keys must retain their identity during conversion.
                           Cover Unicode separators as well as ASCII whitespace. */
                        pattern '[^\p{Z}\p{Cc}]([\s\S]*[^\p{Z}\p{Cc}])?' {
                            error-message "Match condition name must not have leading or trailing whitespace or control characters";
                        }
                    }
                }

                leaf type {
                    description "DHCP packet field to match";
                    mandatory true;
                    type enumeration {
                        enum circuit_id;
                        enum option60;
                    }
                }

                leaf value {
                    description "Exact value to match. For circuit_id this is the SONiC port
                                 alias, the port name when the port has no alias, or a
                                 PortChannel name. For option60 it is the vendor class string.";
                    mandatory true;
                    type string {
                        length 1..255 {
                            error-message "Invalid length for match condition value";
                        }
                    }
                    /* dhcp_relay stamps Option 82 sub-option 1 with the port alias, falling back
                       to the port name when the port has no alias; PortChannels are stamped by
                       name. A circuit_id that resolves to none of these can never match a packet,
                       so reject it at configuration time rather than at service start. */
                    /* not(x = v) rather than x != v: with an absent type the latter is false,
                       which would mask the mandatory-node error. */
                    must "not(../type = 'circuit_id') or " +
                         "/port:sonic-port/port:PORT/port:PORT_LIST[port:alias = current()] or " +
                         "/port:sonic-port/port:PORT/port:PORT_LIST[port:name = current() and not(port:alias)] or " +
                         "/lag:sonic-portchannel/lag:PORTCHANNEL/lag:PORTCHANNEL_LIST[lag:name = current()]" {
                        error-message "circuit_id value must match an existing port alias, an aliasless port name, or a PortChannel name";
                        error-app-tag circuit-id-unknown-port;
                    }
                    must "not(../type = 'circuit_id') or count(" +
                         "/port:sonic-port/port:PORT/port:PORT_LIST[port:alias = current()] | " +
                         "/port:sonic-port/port:PORT/port:PORT_LIST[port:name = current() and not(port:alias)] | " +
                         "/lag:sonic-portchannel/lag:PORTCHANNEL/lag:PORTCHANNEL_LIST[lag:name = current()]) <= 1" {
                        error-message "circuit_id value must not resolve to multiple interfaces";
                        error-app-tag circuit-id-ambiguous-port;
                    }
                }
            }
            /* end of DHCP_SERVER_IPV4_MATCH_LIST */
        }
        /* end of DHCP_SERVER_IPV4_MATCH container */

        container DHCP_SERVER_IPV4_BINDING {

            description "Match condition based DHCPv4 IP pool bindings";

            list DHCP_SERVER_IPV4_BINDING_LIST {

                description "Associates DHCP match conditions with an IPv4 address pool";

                key "name binding";

                leaf name {
                    description "Name of DHCP interface";
                    type leafref {
                        path "/dhcp-server-ipv4:sonic-dhcp-server-ipv4/dhcp-server-ipv4:DHCP_SERVER_IPV4/dhcp-server-ipv4:DHCP_SERVER_IPV4_LIST/dhcp-server-ipv4:name";
                    }
                }

                leaf binding {
                    description "User-defined binding name";
                    type string {
                        length 1..255 {
                            error-message "Invalid length for DHCP binding name";
                        }
                        /* See DHCP_SERVER_IPV4_MATCH_LIST/name: '|' is the Config DB
                           key separator and cannot appear inside a key value. */
                        pattern "[^|]*" {
                            error-message "DHCP binding name must not contain '|'";
                        }
                        pattern '[^\p{Z}\p{Cc}]([\s\S]*[^\p{Z}\p{Cc}])?' {
                            error-message "DHCP binding name must not have leading or trailing whitespace or control characters";
                        }
                    }
                }

                leaf-list matches {
                    description "Match conditions combined using logical AND";
                    min-elements 1;
                    type leafref {
                        path "/dhcp-server-ipv4:sonic-dhcp-server-ipv4/dhcp-server-ipv4:DHCP_SERVER_IPV4_MATCH/dhcp-server-ipv4:DHCP_SERVER_IPV4_MATCH_LIST/dhcp-server-ipv4:name";
                    }
                    ordered-by user;
                }

                leaf-list ips {
                    description "Assigned IPv4 addresses";
                    type inet:ipv4-address;
                    ordered-by user;
                }

                leaf-list ranges {
                    description "Named IPv4 address ranges";
                    type leafref {
                        path "/dhcp-server-ipv4:sonic-dhcp-server-ipv4/dhcp-server-ipv4:DHCP_SERVER_IPV4_RANGE/dhcp-server-ipv4:DHCP_SERVER_IPV4_RANGE_LIST/dhcp-server-ipv4:name";
                    }
                    ordered-by user;
                }

                must "((count(ips) > 0) and (count(ranges) = 0)) or ((count(ranges) > 0) and (count(ips) = 0))" {
                    error-message "Exactly one of 'ips' or 'ranges' must be configured";
                }

                /* The matched packet fields are single valued and the conditions are ANDed,
                   so two conditions of the same type can never both hold. dhcp_cfggen
                   rejects such a binding, but that aborts generation of the entire Kea
                   config, which is fatal at service start, so reject it at configuration
                   time instead. Revisit if a future match type is multi valued. */
                must "count(/dhcp-server-ipv4:sonic-dhcp-server-ipv4/dhcp-server-ipv4:DHCP_SERVER_IPV4_MATCH/dhcp-server-ipv4:DHCP_SERVER_IPV4_MATCH_LIST[dhcp-server-ipv4:name = current()/matches][dhcp-server-ipv4:type = 'circuit_id']) <= 1" {
                    error-message "A binding may reference at most one circuit_id match condition";
                    error-app-tag duplicate-match-type;
                }
                must "count(/dhcp-server-ipv4:sonic-dhcp-server-ipv4/dhcp-server-ipv4:DHCP_SERVER_IPV4_MATCH/dhcp-server-ipv4:DHCP_SERVER_IPV4_MATCH_LIST[dhcp-server-ipv4:name = current()/matches][dhcp-server-ipv4:type = 'option60']) <= 1" {
                    error-message "A binding may reference at most one option60 match condition";
                    error-app-tag duplicate-match-type;
                }
            }
            /* end of DHCP_SERVER_IPV4_BINDING_LIST */
        }
        /* end of DHCP_SERVER_IPV4_BINDING container */
    }
}
