module sonic-high-frequency-telemetry {
    yang-version 1.1;

    namespace "http://github.com/sonic-net/sonic-high-frequency-telemetry";

    prefix sonic-high-frequency-telemetry;

    import sonic-port {
        prefix port;
    }

    import sonic-buffer-pool {
        prefix bpl;
    }

    import sonic-buffer-pg {
        prefix bpg;
    }

    import sonic-buffer-queue {
        prefix bql;
    }

    description "Sub-second counter polling configuration for high-frequency telemetry in SONiC.";

    container sonic-high-frequency-telemetry {
        container HIGH_FREQUENCY_TELEMETRY_PROFILE {
            description "Sub-second counter polling profiles for high-frequency telemetry.";
            list HIGH_FREQUENCY_TELEMETRY_PROFILE_LIST {

                key "name";

                leaf name {
                    type string {
                        length 1..128;
                    }
                    description "Unique name for this telemetry profile.";
                }

                leaf stream_state {
                    mandatory true;
                    type string {
                        pattern "enabled|disabled";
                    }
                    description "Whether this telemetry stream is enabled or disabled.";
                }

                leaf poll_interval {
                    mandatory true;
                    description "The interval to poll counter, unit milliseconds.";
                    type uint32;
                }

                leaf otel_endpoint {
                    description "The endpoint of OpenTelemetry collector. E.G. 192.168.0.100:4318. It will use the local OpenTelemetry collector if this value isn't provided.";
                    type string {
                        length 1..4096;
                    }
                }

                leaf otel_certs {
                    description "The path of certificates for OpenTelemetry collector. E.G. /etc/sonic/otel/cert.private. If this value isn't provided, we will use a non-secure channel.";
                    type string {
                        length 1..4096;
                    }
                }

            }
        }

        container HIGH_FREQUENCY_TELEMETRY_GROUP {
            description "Groups of SAI objects and counters monitored by a high-frequency telemetry profile.";
            list HIGH_FREQUENCY_TELEMETRY_GROUP_LIST {
                key "profile_name group_name";

                leaf profile_name {
                    type leafref {
                        path "/sonic-high-frequency-telemetry:sonic-high-frequency-telemetry/HIGH_FREQUENCY_TELEMETRY_PROFILE/HIGH_FREQUENCY_TELEMETRY_PROFILE_LIST/name";
                    }
                    description "Reference to the parent telemetry profile.";
                }

                leaf group_name {
                    type enumeration {
                        enum PORT;
                        enum BUFFER_POOL;
                        enum QUEUE;
                        enum INGRESS_PRIORITY_GROUP;
                    }
                    description "SAI object type to monitor in this group.";
                }

                leaf-list object_names {
                   description "SAI object instances to poll for this group.";
                   type string;
                   must "( ../group_name = 'PORT' and current() = /port:sonic-port/port:PORT/port:PORT_LIST/port:name )"
                        + " or ( ../group_name = 'BUFFER_POOL' and current() = /bpl:sonic-buffer-pool/bpl:BUFFER_POOL/bpl:BUFFER_POOL_LIST/bpl:name )"
                        + " or ( ../group_name = 'INGRESS_PRIORITY_GROUP' and substring-before(current(), '|') = /bpg:sonic-buffer-pg/bpg:BUFFER_PG/bpg:BUFFER_PG_LIST/bpg:port and re-match(substring-after(current(), '|'), '[0-9]+') )"
                        + " or ( ../group_name = 'QUEUE' and substring-before(current(), '|') = /bql:sonic-buffer-queue/bql:BUFFER_QUEUE/bql:BUFFER_QUEUE_LIST/bql:port and re-match(substring-after(current(), '|'), '[0-9]+') )";
                }

                leaf-list object_counters {
                    description "Counter names to collect for the objects in this group.";
                    type string;
                    must "( ../group_name = 'PORT' and re-match(current(), 'IF_IN_OCTETS|IF_IN_UCAST_PKTS|IF_IN_DISCARDS|IF_IN_ERRORS|IN_CURR_OCCUPANCY_BYTES|IF_OUT_OCTETS|IF_OUT_DISCARDS|IF_OUT_ERRORS|IF_OUT_UCAST_PKTS|OUT_CURR_OCCUPANCY_BYTES|TRIM_PACKETS|DROPPED_TRIM_PACKETS|PAUSE_RX_PKTS|PAUSE_TX_PKTS|PFC_[0-7]_RX_PKTS|PFC_[0-7]_TX_PKTS') )"
                        + " or ( ../group_name = 'BUFFER_POOL' and re-match(current(), 'DROPPED_PACKETS|CURR_OCCUPANCY_BYTES|WATERMARK_BYTES|XOFF_ROOM_WATERMARK_BYTES|CURR_OCCUPANCY_CELLS|WATERMARK_CELLS') )"
                        + " or ( ../group_name = 'INGRESS_PRIORITY_GROUP' and re-match(current(), 'PACKETS|BYTES|CURR_OCCUPANCY_BYTES|WATERMARK_BYTES|XOFF_ROOM_CURR_OCCUPANCY_BYTES|XOFF_ROOM_WATERMARK_BYTES|DROPPED_PACKETS|CURR_OCCUPANCY_CELLS|WATERMARK_CELLS|XOFF_ROOM_CURR_OCCUPANCY_CELLS|XOFF_ROOM_WATERMARK_CELLS') )"
                        + " or ( ../group_name = 'QUEUE' and re-match(current(), 'PACKETS|BYTES|DROPPED_PACKETS|CURR_OCCUPANCY_BYTES|WATERMARK_BYTES|WRED_ECN_MARKED_PACKETS|TRIM_PACKETS|DROPPED_TRIM_PACKETS|CURR_OCCUPANCY_CELLS|WATERMARK_CELLS') )";
                }

            }
        }
    }
}
