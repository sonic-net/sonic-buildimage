module sonic-audit {

    yang-version 1.1;

    namespace "http://github.com/sonic-net/sonic-audit";

    prefix sonic-audit;

    import sonic-types {
        prefix stypes;
    }

    description "AUDIT YANG Module for SONiC OS";

    revision 2024-06-20 {
        description "First Revision";
    }

    container sonic-audit {

        container AUDIT {

            description "AUDIT part of config_db.json";

            container config {

                leaf enable {
                    description "This configuration identicates whether enable audit";
                    type stypes:boolean_type;
                    default "true";
                }
            }
            /* end of container config */
        }
        /* end of container AUDIT */
    }
    /* end of top level container */
}
/* end of module sonic-audit */
