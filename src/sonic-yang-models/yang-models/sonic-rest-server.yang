module sonic-rest-server {

    yang-version 1.1;

    namespace "http://github.com/sonic-net/sonic-rest-server";
    prefix rest-server;

    import ietf-inet-types {
        prefix inet;
    }

    organization
        "SONiC";

    contact
        "SONiC";

    description "REST server YANG Module for SONiC OS";

    revision 2026-05-15 {
        description "Add REST_SERVER table model";
    }

    container sonic-rest-server {

        container REST_SERVER {

            description "REST server configuration.";

            container default {
                description "Default REST server instance configuration.";

                leaf port {
                    type inet:port-number;
                    description "TCP port the REST server listens on.";
                }

                leaf client_auth {
                    type enumeration {
                        enum none;
                        enum cert;
                        enum user;
                    }
                    description "REST server client authentication mode.";
                }

                leaf log_level {
                    type uint8 {
                        range 0..100;
                    }
                    description "REST server log verbosity level.";
                }

                leaf server_crt {
                    type string;
                    description "Local path for the REST server certificate.";
                }

                leaf server_key {
                    type string;
                    description "Local path for the REST server private key.";
                }

                leaf ca_crt {
                    type string;
                    description "Local path for the client CA certificate.";
                }
            }
        }
    }
}
