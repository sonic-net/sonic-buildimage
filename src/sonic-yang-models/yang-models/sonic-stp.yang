module sonic-stp {
    yang-version 1.1;
    namespace "http://github.com/sonic-net/sonic-stp";
    prefix stp;

    import sonic-extension {
        prefix sonic-ext;
    }

    description 
        "SONiC STP YANG model for PVST and MST configurations";
    
    revision 2024-12-30 {
        description 
            "Version01 for combined PVST configurations.";
    }

    extension dependent-on {
        argument "dependency";
        description 
            "Indicates module dependencies";
    }

    grouping vlanModeAttr {
        leaf forward_delay {
            type uint8 {
                range "4..30" {
                    error-message "Invalid Forwarding Delay Value.";
                }
            }
            units seconds;
            default 15;
            description
                "The delay used by STP bridges to transition root, and
                designated ports to forwarding";
        }

        leaf hello_time {
            type uint8 {
                range "1..10" {
                    error-message "Invalid Hello Time value.";
                }
            }
            units seconds;
            default 2;
            description
                "The interval between periodic transmissions of
                configuration messages by designated ports";
        }

        leaf max_age {
            type uint8 {
                range "6..40" {
                    error-message "Invalid Maximum Age Time value.";
                }
            }
            units seconds;
            default 20;
            description
                "The Maximum age of the information transmitted by the
                bridge when it is the root bridge.";
        }

        leaf priority {
            type uint16 {
                range "0..61440" {
                    error-message "Invalid Bridge Priority value.";
                }
            }
            default 32768;
            description
                "The manageable component of the Bridge Identifier";
        }
    }

    grouping interfaceAttr {
        leaf path_cost {
            type uint64 {
                range "1..200000000" {
                    error-message "Invalid Port Path Cost value.";
                }
            }
            default 200;
            description
                "The port's contribution, when it is the Root Port,
                to the Root Path Cost for the Bridge";
        }

        leaf priority {
            type uint8 {
                range "0..240" {
                    error-message "Invalid Port Priority value.";
                }
            }
            default 128;
            description
                "The manageable component of the Port Identifier,
                also known as the Port Priority";
        }
    }

    container sonic-spanning-tree {

        container STP {
            list STP_LIST {
                max-elements 1;
                key "keyleaf";
                leaf keyleaf {
                    type enumeration {
                        enum GLOBAL;
                    }
                    description
                        "Key node identifier. It's value is always GLOBAL";
                }

                leaf mode {
                    type enumeration {
                        enum pvst;
                        enum mst;
                    }
                    mandatory true;
                    description
                        "Spanning tree mode";
                }

                leaf rootguard_timeout {
                    must "../../../STP/STP_LIST[keyleaf='GLOBAL']/mode!='mst'" {
                        error-message "Configuration not allowed in MST mode";
                        error-app-tag stp-invalid;
                    }

                    type uint16 {
                        range "5..600" {
                            error-message "Invalid Root-guard Timeout value.";
                        }
                    }
                    units seconds;
                    description
                        "Once superior BPDUs stop coming on the port, device
                        will wait for a period until root guard timeout before
                        moving the port to forwarding state";
                }

                uses vlanModeAttr;
            }
        }

        container STP_VLAN {
            list STP_VLAN_LIST {
                key "name";
                leaf name {
                    type string;
                    description
                        "Vlan identifier";
                }

                leaf vlanid {
                    type uint16 {
                        range "1..4095" {
                            error-message "Vlan ID out of range";
                            error-app-tag vlanid-invalid;
                        }
                    }
                    description
                        "Vlan identifier number";
                }

                leaf enabled {
                    type boolean;
                    mandatory true;
                    description
                        "Spanning tree enabled/disabled on Vlan";
                }

                uses vlanModeAttr;
            }
        }

        container STP_VLAN_PORT {
            list STP_VLAN_PORT_LIST {
                key "vlan-name ifname";

                leaf vlan-name {
                    type leafref {
                        path "../../../STP_VLAN/STP_VLAN_LIST/name";
                    }
                    description
                        "Reference to Vlan";
                }

                leaf ifname {
                    type leafref {
                        path "../../../STP_PORT/STP_PORT_LIST/ifname";
                    }
                    description
                        "Reference to Ethernet interface or PortChannel";
                }

                uses interfaceAttr;
            }
        }

        container STP_PORT {
            list STP_PORT_LIST {
                key "ifname";
                //sonic-ext:dependent-on "STP_LIST";
                must "/sonic-spanning-tree/STP/STP_LIST" {
                    error-message "STP global configuration must exist";
                }
                leaf ifname {
                    type string;
                    description
                        "Reference to Ethernet interface or PortChannel";
                }

                leaf enabled {
                    type boolean;
                    mandatory true;
                    description
                        "Spanning tree enabled/disabled on Interface";
                }

                leaf root_guard {
                    type boolean;
                    description
                        "Enable/Disable Root guard on port";
                }

                leaf bpdu_guard {
                    type boolean;
                    description
                        "Enable/Disable port BPDU guard";
                }

                leaf bpdu_guard_do_disable {
                    type boolean;
                    description
                        "Port to be disabled when it receives a BPDU";
                }

                leaf uplink_fast {
                    type boolean;
                    description
                        "Enable/Disable uplink-fast on port";
                }

                leaf portfast {
                    must "current()!='true' or ../../../STP/STP_LIST[keyleaf='GLOBAL']/mode='pvst'" {
                        error-message "Configuration not allowed in MST mode";
                        error-app-tag stp-invalid;
                    }
                    type boolean;
                    description
                        "Enable/Disable portfast on port";
                }

                uses interfaceAttr;

                // For MST
                leaf edge_port {
                    type boolean;
                    description
                        "Enable/Disable Edge-port on interface";
                }

                leaf link_type {
                    type enumeration {
                        enum auto;
                        enum shared;
                        enum point-to-point;
                    }
                    description
                        "Specifies the interface's link type. Permissible values
                        are 'shared', 'point-to-point' and 'auto'";
                }
            }
        }

        container STP_MST {
            list STP_MST_LIST {
                max-elements 1;
                key "keyleaf";
                //sonic-ext:dependent-on "STP_LIST";
                must "/sonic-spanning-tree/STP/STP_LIST" {
                    error-message "STP global configuration must exist";
                }

                leaf keyleaf {
                    type enumeration {
                        enum GLOBAL;
                    }
                    description
                        "Key node identifier. It's value is always GLOBAL";
                }

                leaf name {
                    must "../../../STP/STP_LIST[keyleaf='GLOBAL']/mode='mst'" {
                        error-message "Configuration allowed in MST mode";
                        error-app-tag stp-invalid;
                    }
                    type string;
                    description
                        "MST Region name";
                }

                leaf revision {
                    must "../../../STP/STP_LIST[keyleaf='GLOBAL']/mode='mst'" {
                        error-message "Configuration allowed in MST mode";
                        error-app-tag stp-invalid;
                    }
                    type uint32;
                    description
                        "MST Revision number";
                }

                leaf max_hops {
                    must "../../../STP/STP_LIST[keyleaf='GLOBAL']/mode='mst'" {
                        error-message "Configuration allowed in MST mode";
                        error-app-tag stp-invalid;
                    }
                    type uint8;
                    description
                        "MST Max hops";
                }

                leaf hello_time {
                    must "../../../STP/STP_LIST[keyleaf='GLOBAL']/mode='mst'" {
                        error-message "Configuration allowed in MST mode";
                        error-app-tag stp-invalid;
                    }
                    type uint8;
                    description
                        "MST hello time";
                }

                leaf max_age {
                    must "../../../STP/STP_LIST[keyleaf='GLOBAL']/mode='mst'" {
                        error-message "Configuration allowed in MST mode";
                        error-app-tag stp-invalid;
                    }
                    type uint8;
                    description
                        "MST max age";
                }

                leaf forward_delay {
                    must "../../../STP/STP_LIST[keyleaf='GLOBAL']/mode='mst'" {
                        error-message "Configuration allowed in MST mode";
                        error-app-tag stp-invalid;
                    }
                    type uint8;
                    description
                        "MST forward delay";
                }

                leaf hold_count {
                    must "../../../STP/STP_LIST[keyleaf='GLOBAL']/mode='mst'" {
                        error-message "Configuration allowed in MST mode";
                        error-app-tag stp-invalid;
                    }
                    type uint8;
                    description
                        "MST hold count";
                }
            }
        }

        container STP_MST_INST {
            list STP_MST_INST_LIST {
                key "instance";

                leaf instance {
                    type uint16;
                    description
                        "Instance identifier";
                }

                leaf-list vlan {
                    type string;
                    description
                        "Vlan list";
                }

                leaf bridge_priority {
                    type uint16 {
                        range "0..61440" {
                            error-message "Invalid Bridge Priority value.";
                        }
                    }
                    description
                        "The manageable component of the Bridge Identifier";
                }
            }
        }

        container STP_MST_PORT {
            list STP_MST_PORT_LIST {
                key "inst_id ifname";

                leaf inst_id {
                    type leafref {
                        path "../../../STP_MST_INST/STP_MST_INST_LIST/instance";
                    }
                    description
                        "Reference to MST Instance";
                }

                leaf ifname {
                    type leafref {
                        path "../../../STP_PORT/STP_PORT_LIST/ifname";
                    }

                    description
                        "Reference to Ethernet interface or PortChannel";
                }
                uses interfaceAttr;
            }
        }
    }
}
