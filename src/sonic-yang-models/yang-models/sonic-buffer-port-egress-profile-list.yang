module sonic-buffer-port-egress-profile-list {
    namespace "http://github.com/sonic-net/sonic-buffer-port-egress-profile-list";
    prefix bpg;

    import sonic-port {
        prefix prt;
    }

    import sonic-buffer-profile {
        prefix bpf;
    }

    organization
        "SONiC";

    contact
        "SONiC";

    description
        "Assigns egress buffer profiles to ports.";

    revision 2021-07-01 {
        description
            "Initial revision.";
    }

    container sonic-buffer-port-egress-profile-list {

        container BUFFER_PORT_EGRESS_PROFILE_LIST {

            description "Binds egress buffer profiles to ports.";

            list BUFFER_PORT_EGRESS_PROFILE_LIST_LIST {

                key "port";

                description "Egress buffer profile binding for a port.";

                leaf port {
                    type leafref {
                        path "/prt:sonic-port/prt:PORT/prt:PORT_LIST/prt:name";
                    }
                    description "Port to which egress buffer profiles are assigned.";
                }

                leaf-list profile_list {
                    type leafref {
                        path "/bpf:sonic-buffer-profile/bpf:BUFFER_PROFILE/bpf:BUFFER_PROFILE_LIST/bpf:name";
                    }
                    ordered-by user;
                    description "Ordered list of egress buffer profile names applied to this port.";
                }

            }
        }
    }
}
