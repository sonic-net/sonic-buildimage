module sonic-dns {

    namespace  "http://github.com/sonic-net/sonic-dns";
    yang-version 1.1;
    prefix dns;

    import ietf-inet-types {
        prefix inet;
    }

    organization
        "SONiC";

    contact
        "SONiC";

    description "Domain Name System (DNS) resolver configuration";

    revision 2023-02-14 {
        description "Initial version";
    }

    container sonic-dns {

        container DNS_NAMESERVER {

            description "DNS nameserver addresses for name resolution.";

            list DNS_NAMESERVER_LIST {
                max-elements 3;
                description "Ordered list of DNS nameserver IP addresses.";

                key "ip";

                leaf ip {
                    description "IPv4 or IPv6 address of a DNS nameserver.";
                    type inet:ip-address;
                }
            } /* end of list DNS_NAMESERVER_LIST */

        } /* end of container DNS_NAMESERVER */

        container DNS_OPTIONS {
            description "DNS resolver options; requires at least one nameserver to be configured.";

            container GLOBAL {
                leaf-list search {
                    description "Configure the DNS search suffix list";
                    type inet:host;
                }

                leaf ndots {
                    description "Sets a threshold for the number of dots which must appear in a name given before an initial absolute query will be made";
                    type uint8 {
                        range "0..15";
                    }
                    default 1;
                }

                leaf timeout {
                    description "Sets the amount of time in seconds the resolver will wait for a response from a remote name server before retrying the query via a different name server.";
                    type uint8 {
                        range "1..30";
                    }
                    default 5;
                }

                leaf attempts {
                    description "Sets the number of times the resolver will send a query to its name servers before giving up and returning an error to the calling application.";
                    type uint8 {
                        range "1..5";
                    }
                    default 2;
                }
            } /* end of container GLOBAL */

            when "count(../DNS_NAMESERVER/DNS_NAMESERVER_LIST/ip) > 0";
        } /* end of container DNS_OPTIONS */

    } /* end of container sonic-dns */

} /* end of module sonic-dns */
