module sonic-bmp {

    yang-version 1.1;

    namespace "http://github.com/sonic-net/sonic-bmp";
    prefix bmp;

    import sonic-types {
        prefix stypes;
    }

    organization
        "SONiC";

    contact
        "SONiC";

    description "BMP configuration";

    revision 2024-03-20 {
        description "First Revision";
    }

    container sonic-bmp {

        container BMP {

            description "BGP Monitoring Protocol (BMP) table dump configuration.";

            container table {

                leaf bgp_neighbor_table {
                    type stypes:boolean_type;
                    default "true";
                    description "Enable or disable BMP BGP neighbor table dump.";
                }

                leaf bgp_rib_in_table {
                    type stypes:boolean_type;
                    default "false";
                    description "Enable or disable BMP Adj-RIB-In table dump.";
                }

                leaf bgp_rib_out_table {
                    type stypes:boolean_type;
                    default "false";
                    description "Enable or disable BMP Adj-RIB-Out table dump.";
                }

            }

        }

    }

}
