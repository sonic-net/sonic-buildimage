module sonic-neigh {
	yang-version 1.1;
	namespace "http://github.com/sonic-net/sonic-neigh";
	prefix neigh;

	import ietf-inet-types {
		prefix inet;
	}

	import ietf-yang-types {
		prefix yang;
	}

	import sonic-portchannel {
		prefix lag;
	}

	import sonic-port {
		prefix port;
	}
	// TODO: Uncomment the following lines when sonic-vlan.yang is available
	// import sonic-vlan {
	// 	prefix svlan;
	// }

	organization "SONiC";
	contact "SONiC";

	description "NEIGH configuration";

	revision 2023-03-31 {
		description "Initial Revision";
	}

	container sonic-neigh {
		container NEIGH {
			description "NEIGH configuration";
			list NEIGH_LIST {
				key "port neighbor";

				leaf port {
					description "Neighbor interface ex. Vlan1000, PortChannel1024";
					type union {
						type leafref {
							path /lag:sonic-portchannel/lag:PORTCHANNEL/lag:PORTCHANNEL_LIST/lag:name;
						}
						type leafref {
							path /port:sonic-port/port:PORT/port:PORT_LIST/port:name;
						}
						type string {
							pattern "Vlan[0-9]+";
						}
						// TODO: Uncomment the following lines when sonic-vlan.yang is available
						// type leafref {
						// 	path "/svlan:sonic-vlan/svlan:VLAN/svlan:VLAN_LIST/svlan:name";
						// }
					}
				}

				leaf neighbor {
					description "Neighbor IP address ex. 100.1.1.3";
					type inet:ip-address;
				}

				leaf neigh {
					description "Neighbor MAC address";
					type yang:mac-address;
				}

				leaf family {
					description "IP family of Neighbor address";
					type string {
						pattern "IPv4|IPV4|IPv6|IPV6";
					}
				}
			}
		}
	}
}
