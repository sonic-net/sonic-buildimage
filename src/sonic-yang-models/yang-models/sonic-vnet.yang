module sonic-vnet {
    yang-version 1.1;
    namespace "http://github.com/sonic-net/sonic-vnet";
    prefix svnet;

    import ietf-yang-types {
        prefix yang;
    }

    import ietf-inet-types {
        prefix inet;
    }

    import sonic-types {
        prefix stypes;
    }

    import sonic-vxlan {
        prefix svxlan;
    }
    organization
        "SONiC";

    contact
        "SONiC";

    description
        "Virtual Network (VNET) configuration for overlay networking using VxLAN tunnels";

    revision 2026-09-15 {
        description
            "Add install_on_kernel leaf to VNET_ROUTE_TUNNEL_LIST.";
    }

    revision 2023-04-25 {
        description
            "First revision.";
    }

    container sonic-vnet {

        container VNET {

            description "Virtual Network configuration table for overlay networking";

            list VNET_LIST {

                description "Configuration entry for a Virtual Network instance";

                key "name";

                leaf name {
                    description "Unique alphanumeric name identifying the virtual network";
                    type string {
                        length 1..255;
                    }
                }

                leaf vxlan_tunnel {
                    mandatory true;
                    description "A valid and active vxlan tunnel to be used with this vnet for traffic encapsulation.";
                    type leafref {
                        path "/svxlan:sonic-vxlan/svxlan:VXLAN_TUNNEL/svxlan:VXLAN_TUNNEL_LIST/svxlan:name";
                    }
                }

                leaf vni {
                    mandatory true;
                    description "A valid and unique vni which will become part of the encapsulated traffic header.";
                    type stypes:vnid_type;
                }

                leaf peer_list {
                    description "Set of peers";
                    /* Values in leaf list are UNIQUE */
                    type string;
                }

                leaf guid {
                    description "An optional guid.";
                    type string {
                        length 1..255;
                    }
                }

                leaf scope {
                    description "can only be default.";
                    type string {
                        pattern "default" {
                            error-message "Invalid VRF name";
                        }
                    }
                }

                leaf advertise_prefix {
                    description "Flag to enable advertisement of route prefixes belonging to the Vnet.";
                    type  boolean;
                }

                leaf overlay_dmac {
                    description "Overlay Dest MAC address to be used by Vnet ping.";
                    type yang:mac-address;
                }

                leaf src_mac {
                    description "source mac address for the Vnet";
                    type yang:mac-address;
                }

                leaf evpn_enabled {
                    description "Flag to enable EVPN for the Vnet.";
                    type boolean;
                }

                leaf decap_tunnel_list {
                    description "List of additional VXLAN tunnels to decapsulate into this Vnet.";
                    type string;
                }
            }
            /* end of list VNET_LIST */
        }
        /* end of container VNET */

        container VNET_ROUTE {

            description "Static routes within a virtual network";

            list VNET_ROUTE_LIST {
                description "Static route entry within a virtual network";

                key "vnet_name prefix";

                leaf vnet_name {
                    description "VNET name";
                    type leafref {
                        path "/svnet:sonic-vnet/svnet:VNET/svnet:VNET_LIST/svnet:name";
                    }
                }

                leaf prefix {
                    description "IP prefix in CIDR format (IPv4 or IPv6)";
                    type stypes:sonic-ip-prefix;
                }

                leaf nexthop {
                    description "Nexthop IP addresses (IPv4 or IPv6, comma-separated)";
                    type union {
                        type stypes:ipv4-address-list;
                        type stypes:ipv6-address-list;
                    }
                    mandatory true;
                }

                leaf ifname {
                    description "Interface names";
                    type string;
                    mandatory true;
                }
            }
            /* end of list VNET_ROUTE_LIST */
        }
        /* end of container VNET_ROUTE */

        container VNET_ROUTE_TUNNEL {

            description "Tunnel-encapsulated routes within a virtual network";
            
            list VNET_ROUTE_TUNNEL_LIST {
                description "Tunnel-encapsulated route entry for overlay traffic within a virtual network";
                key "vnet_name prefix";

                leaf vnet_name {
                    description "VNET name";
                    type leafref {
                        path "/svnet:sonic-vnet/svnet:VNET/svnet:VNET_LIST/svnet:name";
                    }
                }
                
                leaf prefix {
                    description "IP prefix in CIDR format (IPv4 or IPv6)";
                    type stypes:sonic-ip-prefix;
                }
                
                leaf endpoint {
                    description "Endpoint/nexthop tunnel IPs (IPv4 or IPv6, comma-separated)";
                    type union {
                        type stypes:ipv4-address-list;
                        type stypes:ipv6-address-list;
                    }
                    mandatory true;
                }

                leaf mac_address {
                    description "Inner dest macs in encapsulated packet";
                    type stypes:mac-address-list;
                }

                leaf vni {
                    description "Valid and active vni values in encapsulated packet";
                    type stypes:vnid-list;
                }

                leaf consistent_hashing_buckets {
                    description "Number of consistent hashing buckets to use, if consistent hashing is desired";
                    type uint16;
                }

                leaf metric {
                    description "Value that can be set to categorize or determine the type of route. This value does not affect route behavior.";
                    type uint8;
                }

                leaf install_on_kernel {
                    description "Flag to also program this route into the kernel routing table.";
                    type boolean;
                }
            }
            /* end of list VNET_ROUTE_TUNNEL_LIST */
        }
        /* end of container VNET_ROUTE_TUNNEL */
    }
    /* end of container sonic-vnet */
}
/* end of module sonic-vnet */
