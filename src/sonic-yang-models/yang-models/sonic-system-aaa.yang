module sonic-system-aaa {
    namespace "http://github.com/sonic-net/sonic-system-aaa";
    prefix ssys;
    yang-version 1.1;

    import sonic-types {
        prefix stypes;
    }

    import sonic-system-tacacs{
        prefix tacacs;
    }

    description "Authentication, Authorization, and Accounting (AAA) configuration";

    revision 2021-10-12 {
        description "Add AAA authorization/accounting support.";
    }

    revision 2021-04-15 {
        description "Initial revision.";
    }

    container sonic-system-aaa {
        container AAA {
            description "AAA configuration for local and remote user authentication methods.";
            list AAA_LIST {
                key "type";
                description "AAA method configuration entry keyed by function type.";

                leaf type {
                    type enumeration {
                        enum authentication;
                        enum authorization;
                        enum accounting;
                    }
                    description "AAA function type: authentication, authorization, or accounting.";
                }

                leaf login {
                    type string {
                        pattern '((ldap|tacacs\+|local|radius|default),)*(ldap|tacacs\+|local|radius|default)' {
                            error-message "Invalid login choice";
                        }
                    }
                    description "Ordered list of authentication methods to attempt (radius, tacacs+, ldap, local, or default).";
                    default "local";
                }

                must 'not(./type = "authentication" and contains(./login, "tacacs+") and not(/tacacs:sonic-system-tacacs/tacacs:TACPLUS/tacacs:global/tacacs:passkey))' {
                    error-message "Authentication with 'tacacs+' is not allowed when passkey not exists.";
                }

                leaf failthrough {
                    type stypes:boolean_type;
                    description "When true, authentication continues to the next method in the list upon failure.";
                    default False;
                }

                leaf fallback {
                    type stypes:boolean_type;
                    description "When true, falls back to local authentication if all remote methods fail.";
                    default False;
                }

                leaf debug {
                    type stypes:boolean_type;
                    description "Enable or disable verbose AAA debug logging.";
                    default False;
                }

                leaf trace {
                    type stypes:boolean_type;
                    description "Enable or disable AAA protocol packet tracing.";
                    default False;
                }
            }
        }
    }
}
