module sonic-wred-profile {

    yang-version 1.1;

    namespace "http://github.com/sonic-net/sonic-wred-profile";

    prefix wrd;

    organization
        "SONiC";

    contact
        "SONiC";

    description
        "WRED_PROFILE yang Module for SONiC OS";

    revision 2021-04-01 {
        description
            "Initial revision.";
    }

    container sonic-wred-profile {

        container WRED_PROFILE {

            description "Configures Weighted Random Early Detection profiles for congestion avoidance.";

            list WRED_PROFILE_LIST {

                key "name";

                description "A named WRED profile with per-color thresholds and drop probabilities.";

                leaf name {
                    type string {
                        pattern '[a-zA-Z0-9]{1}([-a-zA-Z0-9_]{0,31})';
                        length 1..32 {
                            error-message "Invalid length for wred profile name.";
                            error-app-tag wred-profile-name-invalid-length;
                        }
                    }
                    description "WRED profile name";
                }

                /* Thresholds are bounded to the signed 32-bit range that orchagent can parse. */
                leaf yellow_min_threshold {
                    type uint64 {
                        range "0..2147483647";
                    }
                    units bytes;
                    description "Queue depth in bytes at which WRED begins dropping yellow-colored packets.";
                }

                leaf green_min_threshold {
                    type uint64 {
                        range "0..2147483647";
                    }
                    units bytes;
                    description "Queue depth in bytes at which WRED begins dropping green-colored packets.";
                }

                leaf red_min_threshold {
                    type uint64 {
                        range "0..2147483647";
                    }
                    units bytes;
                    description "Queue depth in bytes at which WRED begins dropping red-colored packets.";
                }

                leaf yellow_max_threshold {
                    type uint64 {
                        range "0..2147483647";
                    }
                    units bytes;
                    must "(current() >= current()/../yellow_min_threshold)" {
                        error-message "Yellow max threshold must be greater than or equal to min threshold";
                    }
                    description "Queue depth in bytes at which WRED drops all yellow-colored packets.";
                }

                leaf green_max_threshold {
                    type uint64 {
                        range "0..2147483647";
                    }
                    units bytes;
                    must "(current() >= current()/../green_min_threshold)" {
                         error-message "Green max threshold must be greater than or equal to min threshold";
                    }
                    description "Queue depth in bytes at which WRED drops all green-colored packets.";
                }

                leaf red_max_threshold {
                    type uint64 {
                        range "0..2147483647";
                    }
                    units bytes;
                    must "(current() >= current()/../red_min_threshold)" {
                        error-message "Red max threshold must be greater than or equal to min threshold";
                    }
                    description "Queue depth in bytes at which WRED drops all red-colored packets.";
                }

                leaf ecn {

                    type enumeration {

                        enum ecn_none {
                            description "Disable ECN marking for all colors.";
                        }

                        enum ecn_green {
                            description "Enable ECN marking for green color. Yellow and red are disabled.";
                        }

                        enum ecn_yellow {
                            description "Enable ECN marking for yellow color. Green and red are disabled.";
                        }

                        enum ecn_red {
                            description "Enable ECN marking for red color. Green and red are disabled.";
                        }

                        enum ecn_green_yellow {
                            description "Enable ECN marking for green and yellow colors. Red is disabled.";
                        }

                        enum ecn_green_red {
                            description "Enable ECN marking for green and red colors. Yellow is disabled.";
                        }

                        enum ecn_yellow_red {
                            description "Enable ECN marking for yellow and red colors. Green is disabled.";
                        }

                        enum ecn_all {
                            description "Enable ECN marking for all colors.";

                        }
                    }
                    default ecn_none;
                    description "ECN mode";
                }

                leaf wred_green_enable {
                    type boolean;
                    default false;
                    description "Enable WRED for green-colored traffic.";
                }

                leaf wred_yellow_enable {
                    type boolean;
                    default false;
                    description "Enable WRED for yellow-colored traffic.";
                }

                leaf wred_red_enable {
                    type boolean;
                    default false;
                    description "Enable WRED for red-colored traffic.";
                }

                leaf yellow_drop_probability {
                    type uint64 {
                        range "0..100";
                    }
                    units percent;
                    default 100;
                    description "Maximum drop probability for yellow-colored packets between min and max thresholds.";
                }

                leaf green_drop_probability {
                    type uint64 {
                        range "0..100";
                    }
                    units percent;
                    default 100;
                    description "Maximum drop probability for green-colored packets between min and max thresholds.";
                }

                leaf red_drop_probability {
                    type uint64 {
                        range "0..100";
                    }
                    units percent;
                    default 100;
                    description "Maximum drop probability for red-colored packets between min and max thresholds.";
                }
            }
        }
    }
}
