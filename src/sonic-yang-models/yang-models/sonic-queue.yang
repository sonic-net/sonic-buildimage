module sonic-queue {

    yang-version 1.1;

    namespace "http://github.com/sonic-net/sonic-queue";

    prefix squeue;

    import sonic-extension {
        prefix sonic-ext;
    }

    import sonic-port {
        prefix port;
    }

    import sonic-scheduler {
        prefix sch;
    }

    import sonic-wred-profile {
        prefix wrd;
    }

    import sonic-device_metadata {
        prefix sdm;
    }

    import sonic-types {
        prefix stypes;
    }

    organization
        "SONiC";

    contact
        "SONiC";

    description
	"QUEUE configuration";

    revision 2021-04-01 {
        description
            "Initial revision";
    }

    container sonic-queue {

        container QUEUE {

            description "Configures egress queue scheduling and WRED profiles per port.";

            list QUEUE_LIST {
                when "not(/sdm:sonic-device_metadata/sdm:DEVICE_METADATA/sdm:localhost/sdm:switch_type) or
                    (/sdm:sonic-device_metadata/sdm:DEVICE_METADATA/sdm:localhost/sdm:switch_type!='voq')";

                key "ifname qindex";

                description "Queue entry for a non-VOQ port.";

//         sonic-ext:key-pattern "QUEUE|{ifname}|{qindex}"; //special pattern used for extracting keys from redis-key and populate the yang instance
                                                                 // Total list instances = number(key1) * number(key2) * number(key3)

                leaf ifname {
                    type union {
                        type leafref {
                            path "/port:sonic-port/port:PORT/port:PORT_LIST/port:name";
                        }
                        type string {
                            pattern "CPU";
                        }
                    }
                    description "Interface name.";
                }
                // qindex format is (X) | (X-Y). X is start and Y is end index.
                // X and Y value depends on platform, example for physical ports 0-7 and
                // for CPU port 0-48. Example qindex is 3-4
                leaf qindex {
                  //  sonic-ext:custom-validation ValidateQindexPattern;
                    type string;
                    description "Queue index on the interface.";
                }

                leaf scheduler {
                    type leafref {
                        path "/sch:sonic-scheduler/sch:SCHEDULER/sch:SCHEDULER_LIST/sch:name"; //Reference to SCHEDULER table
                    }
                    description "Scheduler for queue.";
                }

                leaf wred_profile {
                    type leafref {
                        path "/wrd:sonic-wred-profile/wrd:WRED_PROFILE/wrd:WRED_PROFILE_LIST/wrd:name"; // Reference to WRED_PROFILE table
                    }
                    description "Wred profile for queue.";
                }
            }

            list VOQ_QUEUE_LIST {
                when "boolean(/sdm:sonic-device_metadata/sdm:DEVICE_METADATA/sdm:localhost/sdm:switch_type) and
                    (/sdm:sonic-device_metadata/sdm:DEVICE_METADATA/sdm:localhost/sdm:switch_type='voq')";
                key "hostname asic_name ifname qindex";

                description "Queue entry for a VOQ chassis port.";

                leaf hostname {
                    type stypes:hostname;
                    description "VOQ chassis hostname owning this port.";
                }

                leaf asic_name {
                    type stypes:asic_name;
                    description "ASIC instance name within the VOQ chassis.";
                }

                leaf ifname {
                    // Union: try the leafref branch first; if the value resolves to a
                    // PORT row the leafref is satisfied. If not, the plain string
                    // branch accepts the value (used for entries that belong to a
                    // remote linecard/ASIC whose PORT rows live in a different
                    // namespace and therefore cannot be checked locally).
                    //
                    // The must below makes the leafref branch *required* whenever the
                    // row's (hostname, asic_name) matches DEVICE_METADATA/localhost.
                    // For non-local rows the must short-circuits and only the string
                    // branch needs to accept. The gate also degrades to a no-op when
                    // DEVICE_METADATA/localhost is missing hostname or asic_name.
                    // Comparison is case-sensitive; SONiC writes asic_name as
                    // lowercase 'asicN' by convention.
                    type union {
                        type leafref {
                            path "/port:sonic-port/port:PORT/port:PORT_LIST/port:name";
                            require-instance true;
                        }
                        type string {
                            length 1..128;
                        }
                    }
                    must "not(../hostname = /sdm:sonic-device_metadata/sdm:DEVICE_METADATA/sdm:localhost/sdm:hostname
                              and ../asic_name = /sdm:sonic-device_metadata/sdm:DEVICE_METADATA/sdm:localhost/sdm:asic_name)
                          or /port:sonic-port/port:PORT/port:PORT_LIST[port:name = current()]" {
                        error-message "Local VOQ_QUEUE entry (matching DEVICE_METADATA/localhost hostname and asic_name) must reference an existing PORT.";
                        error-app-tag voq-queue-local-port-missing;
                    }
                    description "Interface name on the (possibly remote) VOQ chassis ASIC. Leafref to PORT is enforced only for local entries; remote entries fall through to the string branch.";
                }
                // qindex format is (X) | (X-Y). X is start and Y is end index.
                // X and Y value depends on platform, example for physical ports 0-7 and
                // for CPU port 0-48. Example qindex is 3-4
                leaf qindex {
                  //  sonic-ext:custom-validation ValidateQindexPattern;
                    type string;
                    description "Queue index on the interface.";
                }

                leaf scheduler {
                    type leafref {
                        path "/sch:sonic-scheduler/sch:SCHEDULER/sch:SCHEDULER_LIST/sch:name"; //Reference to SCHEDULER table
                    }
                    description "Scheduler for queue.";
                }

                leaf wred_profile {
                    type leafref {
                        path "/wrd:sonic-wred-profile/wrd:WRED_PROFILE/wrd:WRED_PROFILE_LIST/wrd:name"; // Reference to WRED_PROFILE table
                    }
                    description "Wred profile for queue.";
                }
            }
        }

    }
}
