module sonic-dot1p-tc-map {

    yang-version 1.1;

    namespace "http://github.com/sonic-net/sonic-dot1p-tc-map";

    prefix dot1ptm;

    import sonic-types {
        prefix stypes;
    }

    organization
        "SONiC";

    contact
        "SONiC";

    description
        "DOT1P_TO_TC_MAP yang Module for SONiC OS";

    revision 2021-04-15 {
        description
            "Initial revision.";
    }

    container sonic-dot1p-tc-map {

        container DOT1P_TO_TC_MAP {

            description "Maps 802.1p priority values (0-7) to traffic class for QoS classification.";

            list DOT1P_TO_TC_MAP_LIST {

                key "name";

                description "A named 802.1p to traffic class map.";

                leaf name {
                    type string {
                        pattern '[a-zA-Z0-9]{1}([-a-zA-Z0-9_]{0,31})';
                        length 1..32 {
                            error-message "Invalid length for map name.";
                            error-app-tag map-name-invalid-length;
                        }
                    }
                    description "Name of the DOT1P to TC map.";
                }

                list DOT1P_TO_TC_MAP {

                    key "dot1p";

                    description "Single mapping entry from a DOT1P value to a traffic class.";

                    leaf dot1p {
                        type string {
                            pattern "[0-7]?" {
                                error-message "Invalid DOT1P";
                                error-app-tag dot1p-invalid;
                            }
                        }
                        description "IEEE 802.1p priority value (0-7).";
                    }

                    leaf tc {
                        type stypes:tc_type;
                        description "Target traffic class.";
                    }
                }
            }
        }
    }
}
