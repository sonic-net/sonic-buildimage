module sonic-vxlan {
    yang-version 1.1;
    namespace "http://github.com/sonic-net/sonic-vxlan";
    prefix svxlan;

    import ietf-inet-types {
        prefix inet;
    }
    // Comment sonic-vlan import here until libyang back-links issue is resolved for VLAN leaf reference.
    //import sonic-vlan {
    //    prefix svlan;
    //}
    import sonic-types {
        prefix stypes;
    }

    organization
        "SONiC";

    contact
        "SONiC";

    description
        "VXLAN tunnel and EVPN NVO configuration for SONiC.";

    revision 2021-04-12 {
        description
            "First revision.";
    }

    container sonic-vxlan {

        container VXLAN_TUNNEL {

            description "VXLAN tunnel endpoint (VTEP) definitions including source and destination IP addresses.";

            list VXLAN_TUNNEL_LIST {

                key "name";
                max-elements 2;

                leaf name {
                    description "VXLAN tunnel name.";
                    type string;
                }

                leaf src_ip {
                    description "Source VTEP IP address for tunnel origination.";
                    type inet:ip-address;
                }

                leaf dst_ip {
                    description "Destination VTEP IP address for point-to-point tunnels.";
                    type inet:ip-address;
                }

                leaf ttl_mode {
                    description "Decap TTL mode";
                    type string {
                        pattern "uniform|pipe";
                    }
                }
            }
        }

        container VXLAN_TUNNEL_MAP {

            description "Mappings between VLAN and VNI for a VXLAN tunnel.";

            list VXLAN_TUNNEL_MAP_LIST {
                key "name mapname";

                leaf name {
                    description "Reference to the parent VXLAN tunnel.";
                    type leafref {
                        path "/svxlan:sonic-vxlan/svxlan:VXLAN_TUNNEL/svxlan:VXLAN_TUNNEL_LIST/svxlan:name";
                    }
                }

                leaf mapname {
                    description "Name of the VLAN-to-VNI mapping entry.";
                    type string;
                }

                leaf vlan {
                    description "VLAN associated with this mapping.";
                    mandatory true;
                    // Comment VLAN leaf reference here until libyang back-links issue is resolved and use VLAN string pattern
                    // type leafref {
                    //    path "/svlan:sonic-vlan/svlan:VLAN/svlan:VLAN_LIST/svlan:name";
                    //}
                    type string {
                        pattern 'Vlan([0-9]{1,3}|[1-3][0-9]{3}|[4][0][0-8][0-9]|[4][0][9][0-4])';
                    }

                }

                leaf vni {
                    description "VXLAN Network Identifier mapped to the VLAN.";
                    mandatory true;
                    type stypes:vnid_type;
                }
            }
        }

        container VXLAN_EVPN_NVO {

            description "EVPN Network Virtualization Overlay instance binding a source VTEP.";

            list VXLAN_EVPN_NVO_LIST {

                key "name";
                max-elements 1;

                leaf name {
                    description "EVPN NVO instance name.";
                    type string;
                }

                leaf source_vtep {
                    description "Reference to the VXLAN tunnel used as the source VTEP.";
                    mandatory true;
                    type leafref {
                        path "/svxlan:sonic-vxlan/svxlan:VXLAN_TUNNEL/svxlan:VXLAN_TUNNEL_LIST/svxlan:name";
                    }
                }
            }
        }
    }
}
