module test-grouping {

    namespace "http://test-grouping";
    prefix tg;

    yang-version 1.1;

    import sonic-extension {
        prefix ext;
    }

    revision 2024-01-01 {
        description "Test uses compilation with container/list/uses in groupings";
    }

    grouping group-with-container {
        container settings {
            leaf enabled {
                type string;
            }
            leaf mode {
                type string;
            }
        }
    }

    grouping group-with-list {
        list member {
            key "id";
            leaf id {
                type string;
            }
            leaf value {
                type string;
            }
        }
    }

    grouping simple-fields {
        leaf description {
            type string;
        }
    }

    grouping nested-uses-group {
        uses simple-fields;
        leaf extra {
            type string;
        }
    }

    container test-grouping {

        container TEST_GROUPING_TABLE {

            list TEST_GROUPING_LIST {
                key "name";

                leaf name {
                    type string;
                }

                uses group-with-container;
                uses group-with-list;
                // create-only via refine: must survive libyang refine→target
                // extension copy so get_create_only_fields() sees it.
                // description is nested (nested-uses-group → simple-fields);
                // extra is declared directly on nested-uses-group (shipping shape).
                uses nested-uses-group {
                    refine description {
                        ext:create-only;
                    }
                    refine extra {
                        ext:create-only;
                    }
                }
            }
        }
    }

    notification test-event {
        uses simple-fields;
        leaf event-data {
            type string;
        }
    }
}
